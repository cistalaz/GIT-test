# Specification Title

# Specification: Specification Document
- Description: Requirements Document

## R1
Übereinstimmung mit der Regelung ECE-R125 - Sichtfeld des Fahrers
- Aktiv: true
- Art der Anforderung: Festanaforderung
- Quelle: ECE-R125
- Ursprung / Begründung der Anforderung: Zulassungsfähigkeit
- Urheber: Tobias Oetermann

### R2
Sichtfeld des Fahrers nach vorne (180°)
- Aktiv: true
- Art der Anforderung: Festanaforderung
- Quelle: ECE-R125
- Ursprung / Begründung der Anforderung: Zulassungsfähigkeit
- Bemerkung: Das entwickelten Anzeigesystem im (erweiterten) HUD muss den gesetzlichen Mindestanforderungen an das Sichtfeld des Fahrers/Nutzers entsprechen. Eine Verdeckung innerhalb des nachstehenden Bereichs ist demnach nicht bzw. nur in Ausnahmefällen zulässig und muss gesondert geprüft werden:
  
  - Unterhalb einer horizontalen eben durch V1
  - Oberhalb dreier Ebenen durch V2:
  1. Sekrecht auf X-Z Ebene und gegen die Horizontale um 4° nach vor unten geneigt
  2. Senkrecht auf  Y-Z Ebene und um 4° gegen die Horizontale nach unten geneigt
  3. Senkrecht auf Y-Z Ebene und um 4° gegen die Horizontale nach unten geneigt (an Y-Z ebene gespiegelt)
  
  
  Erläuterung (Bild) ECE-R125 Abbildung 4*
  Bestimmung der V-punkte ECE-R125 Abbildung 1*
- Urheber: Tobias Oetermann
- Verantwortlichkeit: Saint Gobain
- Link -> R258
- Link -> R36

## R3
Übereinstimmung mit der Regelung ECE-R21 Innenausstattung der Kraftfahrzeuge
- Aktiv: true
- Art der Anforderung: Festanaforderung
- Quelle: ECE-R21
- Ursprung / Begründung der Anforderung: Zulassungsfähigkeit
- Urheber: Tobias Oetermann

### R4
Enegieableitende Gestaltung von Systemkomponenten innerhalb des Aufschlagbereiches des Kopfes
- Aktiv: true
- Art der Anforderung: Festanaforderung
- Quelle: ECE-R21
- Ursprung / Begründung der Anforderung: Zulassungsfähigkeit
- Bemerkung: Systemkomponenten bzw. Teile, welche sich innerhalb des Aufschlagbereiches des Kopfes befinden, sind energieableitend zu gestalten. Ausgenommen sind dabei Komponenten, welche
  
  - weniger als 10 cm von Glasflächen entfernt sind
  - nicht Teil der Instrumententafel sind
  - außerhalb des Aufschlagbereiches vom Pendel berührt werden
  sich näher als 10 cm an den außerhalb des Aufschlagbereichs berührten Teilen befinden
- Urheber: Tobias Oetermann
- Verantwortlichkeit: IKA, Cerence, CanControls, Charamel, Saint Gobain

### R5
Konforme Auslegung von Schalter, Knöpfen u.ä. (3,2 - 9,5 mm Offset zur Instrumententafel)
- Aktiv: true
- Art der Anforderung: Festanaforderung
- Quelle: ECE-R21
- Ursprung / Begründung der Anforderung: Zulassungsfähigkeit
- Bemerkung: Schalter, Knöpfe u.ä., welche zwischen 3,2 mm und 9,5 mm aus der Instrumententafel herausragen, müssen eine Querschnittfläche von mindestens 2 cm2 aufweisen (2,5 mm von dem am weitesten hervorstehenden teil gemessen) und abgerundete Kanten haben (Krümmungsradius ≥ 2,5 mm).
  Relevante Ausnahme: Die herausragenden teile sind aus weichem Material der Härte von weniger als 50 Shore A
- Urheber: Tobias Oetermann
- Verantwortlichkeit: IKA, Cerence, CanControls, Charamel, Saint Gobain

### R6
Konforme Auslegung von Schalter, Knöpfen u.ä. (Offset zur Instrumententafel ≥ 9,5 mm)
- Aktiv: true
- Art der Anforderung: Festanaforderung
- Quelle: ECE-R21
- Ursprung / Begründung der Anforderung: Zulassungsfähigkeit
- Bemerkung: Schalter, Knöpfe u.ä., welche mehr als 9,5 mm aus der Instrumententafel herausragen, müssen so beschaffen sein, dass sie unter der Wirkung einer längs wirkenden Horizontalkraft von 37,8 daN entweder in die Oberfläche der Instrumententafel zurückgedrückt werden, so dass sie nicht mehr als 9,5 mm herausragen oder abgetrennt wird (verbleibende Vorsprünge dürfen nicht mehr als 9,5 mm herausragen).  Ein Querschnitt im Abstand von 6,5 mm von dem am weitesten herausragenden Punkt muss eine Fläche von mindestens 6,5 cm2 haben.
  Relevante Ausnahme: Die herausragenden teile sind aus weichem Material der Härte von weniger als 50 Shore A
- Urheber: Tobias Oetermann
- Verantwortlichkeit: IKA, Cerence, CanControls, Charamel, Saint Gobain

### R7
Konforme Auslegung sonstiger Griffe, Hebel, herausstehender Teile
- Aktiv: true
- Art der Anforderung: Festanaforderung
- Quelle: ECE-R21
- Ursprung / Begründung der Anforderung: Zulassungsfähigkeit
- Bemerkung: Sonstige herausstehede Teile im Fahrgastraum, die sich vor der Querebene befindet, welche durch die Bezugslinie des Rumpfes der auf den hintersten Sitz aufgesetzten Prüfpuppe verläuft, unterliegen folgenden Anforderungen (sofern sich ein Insasse des Fahrzeugs an den Teilen stoßen kann):
  
  - Die Oberfläche muss in abgerundeten Kanten auslaufen (Krümmungsradius ≥3,2 mm)
  - Hebel und Knöpfe der Betätigungseinreichtung müssen sich unter der Wirkung einer nach vorn gerichteten horizontalen Längskraft von 37,8 daN in der ungünstigsten Stellung auf einen maximalen Vorsprung von 25 mm von der Oberfläche der Verkleidung stauchen lassen ablösen oder verbiegen (ohne verbleibende gefährliche Vorsprünge)
  - Hansdbrems- oder Gangwahlhebel müssen in der relevanten Situation (gelöst bzw. mit eingelegtem Vorwärtsgang) sofern sie sich oberhalb des H-Punktes des Vordersitze befinden eine Oberfläche von mindestens 6,5 cm2 aufweisen (gemessen am Querschnitt im rechten Winkel zur längs gerichteten Horizontalrichtung und in keinem größeren Abstand als 6,5 mm von dem am weitesten hervorstehenden Teil). Die Krümmungsradien dürfen nicht kleiner als 3,2 mm sein.
  
  Relevante Ausnahme: Teile, welche sich unterhalb der Horizontallinie durch den „H“-Punkt eines jeden Sitzplatzes befinden, unterliegen keiner Vorschrift (unabhängig ob der Insasse damit in berührung kommt)
- Urheber: Tobias Oetermann
- Verantwortlichkeit: IKA

### R8
Konforme Auslegung am Dach befestigter Elemente
- Aktiv: true
- Art der Anforderung: Festanaforderung
- Quelle: ECE-R21
- Ursprung / Begründung der Anforderung: Zulassungsfähigkeit
- Bemerkung: Elemente, welche nicht zur Dachkonstruktion gehören, müssen einen Krümmungsradius von mindestens 3,2 mm aufweisen. Außerdem dar die Breite der vorspringenden Teile nicht kleiner sein als das senkrechte Maß des vorstehenden Teils (ansonsten müssen die teile energieableitend gestaltet werden).
- Urheber: Tobias Oetermann
- Verantwortlichkeit: IKA, Cerence, CanControls, Charamel, Saint Gobain

## R122
Übereinstimmung mit der Regelung ECE-R10 - Einheitliche Bedingungen für die Genehmigung der Fahrzeuge hinsichtlich der elektromagnetischen Verträglichkeit
- Aktiv: true
- Art der Anforderung: Festanaforderung
- Quelle: ECE-R10
- Urheber: Tobias Oetermann
- Ursprung / Begründung der Anforderung: Kompatibilität

### R123
Vorschriften für andere Konfigurationen als „RESS (rechargeableenergystoragesystem—wiederaufladbares Energiespeichersystem) im Ladebetrieb mit dem Versorgungsnetz gekoppelt“
- Aktiv: true
- Art der Anforderung: Festanaforderung
- Quelle: ECE-R10
- Bemerkung: Die Elektrische/Elektronische Unterbaugruppe(n) (EUB) ist bzw. sind auf gestrahlte und leitungsgeführte Störungen und auf Störfestigkeit gegenüber gestrahlten und leitungsgeführten Störungen zu prüfen.
- Ursprung / Begründung der Anforderung: Kompatibilität
- Urheber: Tobias Oetermann
- Verantwortlichkeit: IKA, Cerence, CanControls, Charamel, Saint Gobain

### R124
Vorschriften zur breitbandigen Störaussendung von EUBs
- Aktiv: true
- Art der Anforderung: Festanaforderung
- Quelle: ECE-R10
- Urheber: Tobias Oetermann
- Bemerkung: Werden Messungen nach dem Regelung durchgeführt, sind die Grenzwerte 62-52 dBμV/m im Frequenzbereich von 30-75 MHz, wobei dieser Grenzwert bei Frequenzen über 30 MHz logarithmisch abfällt, und 52-63 dBμV/m im Frequenzbereich von 75-400 MHz, wobei dieser Grenzwert bei Frequenzen über 75 MHz nach Anlage 6 logarithmisch ansteigt. Im Frequenzbereich von 400-1 000 MHz bleibt der Grenzwert konstant bei 63 dB μV/m.
- Ursprung / Begründung der Anforderung: Kompatibilität
- Verantwortlichkeit: IKA, Cerence, CanControls, Charamel, Saint Gobain

### R125
Vorschriften zur schmalbandigen elektromagnetischen Störaussendung von EUBs
- Aktiv: true
- Art der Anforderung: Festanaforderung
- Quelle: ECE-R10
- Urheber: Tobias Oetermann
- Ursprung / Begründung der Anforderung: Kompatibilität
- Bemerkung: Werden Messungen nach dem Regelung durchgeführt, sind die Grenzwerte 52-42 dBμV/m im Frequenzbereich von 30-75 MHz, wobei dieser Grenzwert bei Frequenzen über 30 MHz logarithmisch abfällt, und 42-53 dBμV/m im Frequenzbereich von 75-400 MHz, wobei dieser Grenzwert bei Frequenzen über 75 MHz nach Anlage 7 logarithmisch ansteigt. Im Frequenzbereich von 400-1 000 MHz bleibt der Grenzwert konstant bei 53 dB μV/m.
- Verantwortlichkeit: IKA, Cerence, CanControls, Charamel, Saint Gobain

### R126
Vorschriften über die Störfestigkeit von EUBs gegen elektromagnetische Strahlung
- Quelle: ECE-R10
- Urheber: Tobias Oetermann
- Ursprung / Begründung der Anforderung: Kompatibilität
- Aktiv: true
- Art der Anforderung: Festanaforderung
- Bemerkung: Werden die Prüfungen nach den Regelung beschriebenen Verfahren durchgeführt, sind die Werte der Störfestigkeit: 60 Volt/m (Effektivwert) für die 150-mm-Streifenleitungs-Messmethode, 15 Volt/m (Effektivwert) für die 800-mm-Streifenleitungs-Messmethode, 75 Volt/m (Effektivwert) für die TEM-Zellen-Messmethode (Transversal-Elektro-Magnetisch), 60 mA (Effektivwert) für die Stromeinspeisungs-(BCI)-Messmethode und 30 Volt/m (Effektivwert) für die Methode der Feldeinstrahlung in über 90 % des Frequenzbereichs von 20-2 000 MHz und mindestens 50 Volt/m (Effektivwert) für die 150-mm-Streifenleitungs-Messmethode, 12,5 Volt/m (Effektivwert) für die 800-mm-Streifenleitungs-Messmethode, 62,5 Volt/m (Effektivwert) für die TEM-Zellen-Messmethode, 50 mA (Effektivwert) für die Stromeinspeisungs-Messmethode und 25 Volt/m (Effektivwert) für die Methode der Feldeinstrahlung im gesamten Frequenzbereich von 20-2 000 MHz
  Bei der für ihren Typ repräsentativen EUB gelten die Vorschriften über die Störfestigkeit als eingehalten, wenn bei den Prüfungen nach Regelung keine Leistungsminderung der „Funktionen im Zusammenhang mit der Störfestigkeit“ festgestellt werden kann.
- Verantwortlichkeit: IKA, Cerence, CanControls, Charamel, Saint Gobain

## R9
Übereinstimmung mit dem Standard ISO 3958 - Handreichweite des Fahrzeugführers
- Aktiv: true
- Art der Anforderung: Festanaforderung
- Quelle: ISO 3958
- Ursprung / Begründung der Anforderung: Benutzbarkeit
- Urheber: Tobias Oetermann

### R10
Erreichbarkeit der Anzeige- (Touch) und Bedienelemente
- Quelle: ISO 3958
- Art der Anforderung: Festanaforderung
- Aktiv: true
- Ursprung / Begründung der Anforderung: Benutzbarkeit
- Bemerkung: Für Nutzung des Systems notwendigen Bedienteile (sowie, im Falle einer Touch-Oberfläche, die Anzeige-Elemente) müssen in der Handreichweite des Nutzers sein.
  
  Dreidimensionale und zu greifende Bedienteile dürfen maximal auf den folgenden Hüllkurven platziert werden (Norm bezieht sich auf Drehknöpfe, welche mit 3 Fingern bedient werden; für die Bedienung mit ausgestrecktem Finger (drücken) können die folgenden Hüllkurven um 50 mm verschoben werden):
  
  ISO 3958:1996(E) - Figure 3*
  
  Vorgehen:
  Die Hüllkurven sind relativ zu den eingezeichneten Referenzebenen zu platzieren:
  • Die horizontale Ebene geht durch den R-Punkt des Sitzes.
  • Die HR Ebene berechnet sich mithilfe des zu berechnenden G-Faktors (siehe unten) anhand der folgenden Formel: 
  HR = 786 - 99G
  • Auswahl der geeigneten Hüllkurve mithilfe des bestimtmen G-Faktors
  Bestimmung des G-Faktors 
  Der G-Faktor bezieht sich auf das auf das allgemeine Package des Fahrzeuginnenraumes und ist synthetischer Wert, welcher die Sitzkonfiguration des Fahrzeugs beschreibt. Er wird nach der folgenden Formel berechnet:
  
  G = 0,0018Hz - 0,0197β + 0,0027D + 0,0106α - 0,0011Wx + 0,0024Wz + 0,0027γ - 3,0853
  
  ISO 3958:1996(E) - Figure 2 - Vehicle seating configuration*
  
  ISO 3958:1996(E) - Table 1 - Hand-reach envelope restrained - Vehicle range (G < -1,25) - Population mix 50/50 males/females*
  
  ISO 3958:1996(E) - Table 4 - Hand-reach envelope restrained - Vehicle range (-1,25 ≤ G < -0,75) - Population mix 50/50 males/females*
  
  ISO 3958:1996(E) - Table 7 - Hand-reach envelope restrained - Vehicle range (-0,75 ≤ G < -0,25) - Population mix 50/50 males/females*
  
  ISO 3958:1996(E) - Table 10 - Hand-reach envelope restrained - Vehicle range (-0,25 ≤ G < +0,25) - Population mix 50/50 males/females*
  
  ISO 3958:1996(E) - Table 13 - Hand-reach envelope restrained - Vehicle range (+0,25 ≤ G < +0,75) - Population mix 50/50 males/females*
  
  ISO 3958:1996(E) - Table 16 - Hand-reach envelope restrained - Vehicle range (+0,75 ≤ G < +1,25) - Population mix 50/50 males/females*
  
  ISO 3958:1996(E) - Table 19 - Hand-reach envelope restrained - Vehicle range (G ≥ +1,25) - Population mix 50/50 males/females*
- Urheber: Tobias Oetermann
- Verantwortlichkeit: IKA, Cerence, CanControls, Charamel, Saint Gobain
- Link -> R36

## R11
Übereinstimmung mit dem Standard DIN EN 981 - System akustischer und optischer Gefahrensignale und Informationssignale
- Aktiv: true
- Art der Anforderung: Festanaforderung
- Quelle: DIN EN 981
- Ursprung / Begründung der Anforderung: Wiedererkennbarkeit
- Urheber: Tobias Oetermann

### R12
Priorisierung von Warnsignalen (optisch/akustisch)
- Aktiv: true
- Art der Anforderung: Festanaforderung
- Quelle: DIN EN 981
- Ursprung / Begründung der Anforderung: Wiedererkennbarkeit
- Bemerkung: Die Dringlichkeit von Warnsignalen ist deutlich zu priorisieren und die Gestaltung der Warnsignale entsprechend der Dringlichkeit zu gestalten. Für die Priorisierung der Signale gilt die folgende Tabelle als Richtlinie:
  Signale nach Grad der Dringlichkeit DIN EN 981 - Tabelle 1*
- Urheber: Tobias Oetermann
- Verantwortlichkeit: IKA, Cerence, CanControls, Charamel, Saint Gobain

### R13
Konforme Gestaltung von Warnsignalen (akustisch)
- Aktiv: true
- Art der Anforderung: Festanaforderung
- Quelle: DIN EN 981
- Ursprung / Begründung der Anforderung: Wiedererkennbarkeit
- Bemerkung: Um eine Wiedererkennbarkeit der akustischen Warnsignale und der damit einhergehenden Dringlichkeit zu gewährleisten, sind die Signale unter gewissen Gestaltungsparametern zu realisieren. Für die Gestaltung der akustischen Signale gilt die folgende Tabelle als Richtlinie:
  Merkmale akustischer Signale DIN EN 981 - Tabelle 3*
- Urheber: Tobias Oetermann
- Verantwortlichkeit: IKA, Cerence

### R14
Konforme Gestaltung von Warnsignalen (optisch)
- Aktiv: true
- Art der Anforderung: Festanaforderung
- Quelle: DIN EN 981
- Ursprung / Begründung der Anforderung: Wiedererkennbarkeit
- Bemerkung: Um eine Wiedererkennbarkeit der visuellen/optischen Warnsignale und der damit einhergehenden Dringlichkeit zu gewährleisten, sind die Signale unter gewissen Gestaltungsparametern zu realisieren. Für die Gestaltung der visuellen/optischen Signale gilt die folgende Tabelle als Richtlinie:
  Merkmale optischer/visueller Signale DIN EN 981 - Tabelle 4*
- Urheber: Tobias Oetermann
- Verantwortlichkeit: IKA, Saint Gobain, Charamel

## R15
Übereinstimmung mit dem Standard ISO 4513 - Sicht - Methoden zur Messung der Position der Augen eines Fahrers
- Aktiv: true
- Art der Anforderung: Festanaforderung
- Quelle: ISO 4513
- Ursprung / Begründung der Anforderung: Benutzbarkeit
- Urheber: Tobias Oetermann

### R16
Absicherung der Sichtbarkeit visueller Anzeigen
- Aktiv: true
- Art der Anforderung: Festanaforderung
- Quelle: ISO 4513
- Ursprung / Begründung der Anforderung: Benutzbarkeit
- Bemerkung: Die Auslegung und Entwicklung der visuellen Anzeigekonzepte der Systeme muss die zu erwartenden Augenpositionen der Fahrer berücksichtigen. Dies gilt insbesondere für Anzeigekonzepte, welche eine Visualisierung in der Windschutzscheibe beinhalten. Das folgende Vorgehen zur Bestimmung und Positionierung der entsprechenden Augenellipsen gilt als Richtlinien, anhand derer die zu entwickelnden Systeme/Anzeigen zu gestalten sind:
  
  Augenellipsen: Bestimmung der Ellipsenparameter:
  
  Länge der Augenellipsen (ISO 4513:2010(E) - Table 2 & Figure 4)*
  
  Winkel der Augenellipsen
  
  In der Draufsicht (a) - Z-Achse) und der Rückansicht (c) - X-Achse) sind die Augenellipsen mit den Fahrzeugachsen in Flucht. In der Seitenansicht (b) - Y-Achse) ist die Augenellipse hingegen um β = 12° geneigt.
  
  Hinweis:
  Die DIN EN ISO 15008 zur Auslegung und Bewertung der Darstellung optischer Information legt das 95-Perzentil zugrunde.
  Augenellipsen: Bestimmung des Ellipsenschwerpunkts 
  Anmerkung
  Die Position des Schwerpunkts der Augenellipsen bestimmen sich anhand der nachstehenden Formeln. Die Variablen sind der nachstehenden Zeichnung zu entnehmen 
  (mit Ausnahme von t: Kennwert für die Art des Getriebes 
  •	t=1 bei vorhandenem Kupplungspedal
  •	t=0 bei Automatikgetriebe)
  
  ISO 4513:2010(E) - Figure 5 - Eyellipse package factors, side view axis angle and centroid location*
  
  Schwerpunktberechnung:
  
  Xc = L1 + 664 + 0,587 L6 − 0,176 H30 − 12,5 t
  
  YcL = W20 − 32,5
  
  YcR = W20 + 32,5
  
  Zc = H8 + 638 + H30
  
  Augenellipsen: Vorgehen zur Systemauslegung 
  
  Vorgehen:
  1. Sitzcharakteristik bestimmen: A19, W20, H30, TL23
  2. H8 und L6 bestimmen
  3. Festlegung von t anhand der erwarteten Produktionszahlen (bei ≥ 50% mit vorhandenem Kupplungspedal t=1)
  4. Konstruktion der Augenellipsen anhand der gegebenen Tabelle (links und rechts identisch)
  5. Schwerpunkt anhand der gegebenen Formeln bestimmen
  6. Drehung der X-Achse der Ellipsen um β = 12°
- Urheber: Tobias Oetermann
- Verantwortlichkeit: IKA, Saint Gobain, Charamel
- Link -> R25

## R17
Übereinstimmung mit dem Standard DIN EN ISO 15008 - Anforderungen und Bewertungsmethoden der visuellen Informationsdarstellung im Fahrzeug
- Aktiv: true
- Art der Anforderung: Festanaforderung
- Ursprung / Begründung der Anforderung: Benutzbarkeit
- Quelle: DIN EN ISO 15008
- Urheber: Tobias Oetermann

### R18
Helligkeitsregelung des Displays
- Aktiv: true
- Art der Anforderung: Festanaforderung
- Ursprung / Begründung der Anforderung: Benutzbarkeit
- Quelle: DIN EN ISO 15008
- Bemerkung: Die Displaybeleuchtung sollte eine Helligkeitsregelung haben, welche über einen angemessenen Bereich anpassbar ist.
  Relevante Einschränkung: Die Norm gilt explizit nicht für dem äußeren Sichtfeld überlagerte Informationen wie bspw. in Head-Up Displays.
- Urheber: Tobias Oetermann
- Verantwortlichkeit: IKA, Saint Gobain

### R19
Ausreichendes Kontrastverhältnis zwischen Symbol und Hintergrund
- Aktiv: true
- Art der Anforderung: Festanaforderung
- Ursprung / Begründung der Anforderung: Benutzbarkeit
- Quelle: DIN EN ISO 15008
- Bemerkung: Das minimale Kontrastverhältnis zwischen Symbol und Hintergrund muss wie folgt sein: 
  • 5:1 Nachtzustand
  • 3:1 Zwielichtzustand
  • 3:1 Tageszustand
  • 2:1 Zustand mit direktem Sonnenlicht
  Relevante Ausnahme: Ein Zeichen ist absichtlich ausgegraut/transparent etc., um beispielsweise einen inaktiven Zustand zu repräsentieren.
  Bedingung: Bei fest verbauten Displays müssen die Anforderungen vom hintersten Punkt der zyklopischen Augenellipse aus erfüllt werden. Bei verstellbaren Displayausrichtungen darf eine Displayposition gewählt werden, die alle Anforderungen gleichzeitig erfüllt.
  Relevante Einschränkung: Die Norm gilt explizit nicht für dem äußeren Sichtfeld überlagerte Informationen wie bspw. in Head-Up Displays.
- Urheber: Tobias Oetermann
- Verantwortlichkeit: IKA, Saint Gobain, Charamel
- Link -> R133
- Link -> R22

### R20
Konforme Umrissgestaltung von Zeichen/Symbolen (bspw. zur Kontrasterhöhung)
- Aktiv: true
- Art der Anforderung: Festanaforderung
- Quelle: DIN EN ISO 15008
- Ursprung / Begründung der Anforderung: Benutzbarkeit
- Bemerkung: Im Falle von Umrissen um Zeichen/Symbole ist auf folgende Vorgaben zu achten:
  • Zeichen mit Serifen: Verhältnis von Strichbreite des Umrisses zu der Zeichenhöhe < 0,04
  • Zeichen ohne Serifen: Verhältnis von Strichbreite des Umrisses zu der Zeichenhöhe < 0,08
  • Strichbreite des Umrisses ≥ 0,35 mm
  • Es sollte keine umrissene Schriftart mit ungefüllten Zeichen (transparenter Körper) verwendet werden
  → Wenn Vorgaben nicht vereinbar, sollte ein Umriss vermieden werden
- Urheber: Tobias Oetermann
- Verantwortlichkeit: IKA, Saint Gobain, Charamel
- Link -> R22

### R21
Konforme Schattengestaltung von Zeichen/Symbolen (bspw. zur Kontrasterhöhung)
- Aktiv: true
- Art der Anforderung: Festanaforderung
- Quelle: DIN EN ISO 15008
- Ursprung / Begründung der Anforderung: Benutzbarkeit
- Bemerkung: Im Falle von Schatten um Zeichen/Symbole ist auf folgende Vorgaben zu achten:
  • Kontrast zwischen Zeichenkörper/ungefüllten Bereich und dessen Schatten ≥ 75% des minimalen Kontrastes
  • Richtung der Lichtquelle: 25° bis 155° (ausgehend von Horizontalen)
  • Text und Hintergrund dürfen nicht beide in dunkler Farbe sein
  • Schatten und Text dürfen nicht losgelöst sein (kein Abstand zwischen Schatten und Text)
  • Schatten darf durch Größe keine relevanten Informationen im Hintergrund verdecken
  • Schatten sollte einen weichen Übergang zum Hintergrund haben
  • Schattenbreite < 70% der Strichbreite der regulären Schriftart (auch bei Fettdruck)
  Anwendung: Begrenzt auf statischen Kennzeichnungen, nichtdynamischen Texten oder Textfeldtitel
- Urheber: Tobias Oetermann
- Verantwortlichkeit: IKA, Saint Gobain, Charamel

### R22
Konforme Zeichengestaltung bei uneinheitlichen oder dynamischen Hintergründen
- Aktiv: true
- Art der Anforderung: Festanaforderung
- Quelle: DIN EN ISO 15008
- Ursprung / Begründung der Anforderung: Benutzbarkeit
- Bemerkung: Im Falle von uneinheitlichen Hintergründen (verschiedene Leuchtdichten, Farben etc.) um den Text, muss an der ungünstigsten Stelle ein ausreichender Kontrast (siehe Anforderung 12) vorliegen. Bei dynamischen Hintergründen sollte ein zusätzlicher konform gestalteter Umriss vorgesehen werden (siehe Anforderung 13).
- Urheber: Tobias Oetermann
- Verantwortlichkeit: IKA, Saint Gobain, Charamel

### R23
Konforme Auswahl der Anzeigemodi in Abhängigkeit des Umgebungslichtes
- Aktiv: true
- Art der Anforderung: Festanaforderung
- Quelle: DIN EN ISO 15008
- Ursprung / Begründung der Anforderung: Benutzbarkeit
- Bemerkung: Die Durchschnittsleuchtdichte von oft nacheinander betrachteten Bereichen darf nicht zu stark voneinander abweichen, um die Adaption der Augen nicht zu über-strapazieren:
  • Nachtzustand: Negativer Anzeigemodus (helle Symbole auf dunklem Hintergrund)
  • Tageszustand: Negativer oder positiver Anzeigemodus (dunkle Symbole auf hellem Hintergrund)
  • Display ohne Blend-/Reflexionsschutz: Positiver Anzeigemodus
- Urheber: Tobias Oetermann
- Verantwortlichkeit: IKA, Saint Gobain, Charamel
- Link -> R133

### R24
Konforme Auswahl der Farbkombination von Symbol und Hintergrund
- Aktiv: true
- Art der Anforderung: Festanaforderung
- Quelle: DIN EN ISO 15008
- Ursprung / Begründung der Anforderung: Benutzbarkeit
- Bemerkung: Nicht alle Farbkombinationen für Symbol und Hintergrund sind akzeptabel. Bei Vollfarbdisplays sollten daher bestimmte Farbkombinationen anhand der folgenden Tabelle ausgewählt werden:
  Kombinationen von Zeichen-/Hintergrundfarbe DIN EN ISO 15008 - Tabele B.1*
- Urheber: Tobias Oetermann
- Verantwortlichkeit: IKA, Saint Gobain, Charamel

### R25
Konforme Gestaltung der Schriftgröße anhand der Schrifthöhe
- Aktiv: true
- Art der Anforderung: Festanaforderung
- Quelle: DIN EN ISO 15008
- Ursprung / Begründung der Anforderung: Benutzbarkeit
- Bemerkung: Die Textgröße (lateinisch, griechisch, kyrillisch) sollte anhand der Versalhöhe (Höhe des Buchstaben "H") gemessen werden. Die Versalhöhe wird dabei, wie sämtliche weitere Abmessungen von Merkmalen zur Darstellung von Informationen auf Bildschirmen im automotiven Kontext, in Bogenmaß des Sehwinkels gemessen, unter welchen das Merkmal für einen festgelegten Betrachtungspunkt aus gesehen wird. Das Vorgehen zur Messung der Versalhöhe im Fahrzeug ist ebenso wie eine Tabelle mit akzeptablen Zeichenhöhen nachfolgend gegeben:
  Vorgehen zur Bestimmung der Textabmessungen 
  Die Sehwinkel, angegeben in Radiant, werden aus linearen Größen berechnet:
  
  (mathjax-inline(\alpha_{R} = \frac{ x }{d })mathjax-inline)
  
  mit
  
  (mathjax-inline(\alpha_{R})mathjax-inline) "Winkelgröße (in Radiant)"
  (mathjax-inline(x)mathjax-inline) "Lineare Abmessung des Zeichens (hier: Höhe) projiziert auf eine Ebene senkrecht zur Blickrichtung"
  (mathjax-inline(d)mathjax-inline) "Sehabstand vom hintersten Punktet der zyklopischen Augenellipse (siehe Anforderung 12)"
  
  Die Umrechnung in die Winkelgröße αA, ausgedrückt in Bogenminuten, wird anhand der vorherigen Dimensionen wie folgt abgeleitet:
  
  (mathjax-inline(\alpha_{A} = 60(\frac{ 180*x }{\pi * d }))mathjax-inline)
  
  Zeichenhöhe - DIN EN ISO 15008 - Tabelle 1*
  
  Anmerkung: Für Schrifttypen, deren Proportion von x-Höhe (Höhe des Buchstaben "x") zu Versalhöhe kleiner als 65% ist, sollte die Schriftgröße so vergrößert werden, dass deren x-Höhe 70% der empfohlenen Versalhöhe anhand der vorstehenden Tabelle ist.
- Urheber: Tobias Oetermann
- Verantwortlichkeit: IKA, Saint Gobain, Charamel

### R26
Konforme Gestaltung der Schriftgröße anhand der Schriftbreite
- Aktiv: true
- Art der Anforderung: Festanaforderung
- Quelle: DIN EN ISO 15008
- Ursprung / Begründung der Anforderung: Benutzbarkeit
- Bemerkung: Das Verhältnis von Textbreite zur Texthöhe sollte gewissen Grenzen folgen. Als Richtlinie gilt hier, dass das Verhältnis
  Breite von "H"/Höhe von "H"
  zwischen 65% und 80% liegen sollte.
- Urheber: Tobias Oetermann
- Verantwortlichkeit: IKA, Saint Gobain, Charamel
- Link -> R134

### R27
Konforme Gestaltung der Schriftstärke anhand der Strichbreite
- Aktiv: true
- Art der Anforderung: Festanaforderung
- Quelle: DIN EN ISO 15008
- Ursprung / Begründung der Anforderung: Benutzbarkeit
- Bemerkung: Das Verhältnis von Strichbreite zur Oberhöhe (Höhe von Kleinbuchstaben wie "d") sollte gewissen Grenzen folgen. Als Richtlinie gilt hier, dass das Verhältnis
  Breite von Kleinbuchstabe "l"/Höhe von Kleinbuchstabe "l"
  zwischen 10% und 20% liegen sollte.
  Anmerkung: Schriftarten, bei welchen obiges Verhältnis zwischen 8% und 10% liegt, können durch die Vergrößerung der Schriftart angepasst werden.
- Urheber: Tobias Oetermann
- Verantwortlichkeit: IKA, Saint Gobain, Charamel
- Link -> R134

### R28
Konforme Gestaltung der Zeichenabstände
- Art der Anforderung: Festanaforderung
- Aktiv: true
- Quelle: DIN EN ISO 15008
- Ursprung / Begründung der Anforderung: Benutzbarkeit
- Bemerkung: Schriftarten sollten gleichmäßige und proportionale Abstände aufweisen. Es gelten folgende Vorgaben:
  
  Zeichenabstand (Format "Abstand:Wert"):
  • Abstand zwischen zwei vertikalen Linien (z.B. zwischen "l" und "m"): 150 - 240% der Strichbreite
  • Abstand zwischen einem diagonalen und einem vertikalen Strich (z.B. zwischen "v" und "l"): ≥ 85% der Strichbreite 
  • Abstand zwischen zwei diagonalen Zeichen (z.B. zwischen "v" und "v"): keine Berührung
  • Verhältnis von Wortabstand zu Zeichenabstand: 250 - 300%
  • Zeilenabstand: ≥ 100% der (durchschnittlichen) Strichbreite
- Urheber: Tobias Oetermann
- Verantwortlichkeit: IKA, Saint Gobain, Charamel
- Link -> R134

### R29
Konforme Gestaltung der Groß-/Kleinschreibung
- Aktiv: true
- Art der Anforderung: Festanaforderung
- Quelle: DIN EN ISO 15008
- Ursprung / Begründung der Anforderung: Benutzbarkeit
- Bemerkung: Dynamischer Text, speziell Text, der sich auf wichtige Mitteilungen bezieht, sollte in gemischter Schreibweise oder Kleinschreibung erfolgen, es sei denn, es ist national anders vorgegeben. 
  Großschreibung kann für Texte verwendet werden, die permanenter Teil einer Nutzerschnittstelle sind, wie zum Beispiel Schaltflächen und Beschriftungen, da die Häufigkeit und Auftrittswahrscheinlichkeit solcher Texte die Lesbarkeit verbessert.
- Urheber: Tobias Oetermann
- Verantwortlichkeit: IKA, Saint Gobain, Charamel
- Link -> R134

### R30
Notwendige Größe der Zeichenmatrix für alphanumerische Pixelmatrixzeichen
- Aktiv: true
- Art der Anforderung: Festanaforderung
- Quelle: DIN EN ISO 15008
- Ursprung / Begründung der Anforderung: Benutzbarkeit
- Bemerkung: Um auf Zeichenmatrizen die alphanumerischen Pixelmatrixzeichen abbilden zu können, müssen diese eine gewisse Mindestgröße aufweisen. Die Mindestgrößen sind der folgenden Aufführung zu entnehmen:
  
  Mindestmaße für Zeichenmatritzen (Format Anforderung:Größe (Breite x Höhe)):
  • Ausschließlich Großschreibung: 5 x 7
  • Leserlichkeit einzelner Zeichen: 7 x 9
  • Zeichen mit Unterlängen: 7 x 11
  • tief-/hochgestellte Zahlen: 4 x 5
  • Zähler/Nenner von Brüchen (in Einzelposition): 4 x 5
  • Informationen, die sich nicht auf die eigentliche Aufgabe beziehen (z.B. Copyzeichen): 4 x 5
  • Kraftfahrzeugspezifische Symbole (z.B. ISO 2575): 32 x 32 
  (24 x 24 wenn Grauschattierung möglich)
- Urheber: Tobias Oetermann
- Verantwortlichkeit: IKA, Saint Gobain, Charamel

### R31
Minimierung von Reflexionen und Spiegelungen
- Aktiv: true
- Art der Anforderung: Festanaforderung
- Quelle: DIN EN ISO 15008
- Ursprung / Begründung der Anforderung: Benutzbarkeit
- Bemerkung: Sichtbare Reflexionen und Spiegelungen sind auf ein Minimum zu reduzieren. Dazu verwendete zusätzliche Technologien/verfahren dürfen nicht zur Minderung der vorherigen Anforderungen beitragen.
- Urheber: Tobias Oetermann
- Verantwortlichkeit: Saint Gobain, IKA
- Link -> R36

### R32
Bildstabilität
- Aktiv: true
- Art der Anforderung: Festanaforderung
- Quelle: DIN EN ISO 15008
- Ursprung / Begründung der Anforderung: Benutzbarkeit
- Bemerkung: Das Bild sollte weder zeitlich (Flimmern) noch räumliche Instabilitäten aufweisen. Ein Faktor der räumlichen Instabilität sind Spitze-zu-Spitze-Schwankungen in der geometrischen Lage des Bildes innerhalb des Displays (Jitter): Diese Schwankungen dürfen 0,0002 d nicht überschreiten. Dabei ist d der Sehabstand zwischen der Mitte der zyklopischen Augenellipse und der Mitte des Displays.
- Urheber: Tobias Oetermann
- Verantwortlichkeit: IKA, Saint Gobain, Charamel
- Link -> R36

### R33
Gewählter Einsatz von blinkenden Anzeigen und konforme Gestaltung der Blinkfrequenz
- Aktiv: true
- Art der Anforderung: Festanaforderung
- Quelle: DIN EN ISO 15008
- Ursprung / Begründung der Anforderung: Benutzbarkeit
- Bemerkung: Blinkende Darstellungen sollten nur verwendet werden, um die Aufmerksamkeit des Fahrers zu erzielen und ihn über kritische Zustände zu informieren, die ein sofortiges Handeln erfordern. Um Aufmerksamkeit zu erregen, sollte eine Blinkfrequenz zwischen 1 Hz bis 5 Hz mit einer Einschaltzeit zwischen 50 % bis 70 % verwendet werden.
- Urheber: Tobias Oetermann
- Verantwortlichkeit: IKA, Saint Gobain, Charamel

## R34
Übereinstimmung mit dem Standard DIN EN ISO 15005 - Grundsätze des Dialogmanagements und Konformitätsprüfungen
- Aktiv: true
- Art der Anforderung: Festanaforderung
- Quelle: DIN EN ISO 15005
- Urheber: Tobias Oetermann

### R35
Vermeidung nachteiliger Beeinflussung der primären oder sekundären Bedienelemente
- Art der Anforderung: Festanaforderung
- Aktiv: true
- Ursprung / Begründung der Anforderung: Zulassungsfähigkeit
- Quelle: DIN EN ISO 15005
- Bemerkung: Ein System darf nach aktueller Gesetzeslage keine negativen Auswirkungen auf die Reaktion des Fahrzeugs bei Betätigung der primären oder sekundären Bedienelemente haben.
  Automatisierte Fahrzeugführung: Der juristische Status schreibt eine Überstimmbarkeit der Automation mittels der gegebenen primären (und sekundären) Bedienelemente vor. Eine indirekte Fahrzeugführung mittels primären Bedienelement ist somit (Status Quo) nicht zulässig.
- Urheber: Tobias Oetermann
- Verantwortlichkeit: IKA, Cerence, CanControls, Charamel, Saint Gobain

### R36
Gezielte Installation der Systemelemente zur nicht einschränkenden Benutzbarkeit
- Aktiv: true
- Art der Anforderung: Festanaforderung
- Ursprung / Begründung der Anforderung: Benutzbarkeit
- Quelle: DIN EN ISO 15005
- Bemerkung: Die Display- und Bedienelemente des Systems dürfen die Fahraufgabe nicht behindern (direkte/indirekte Sicht, Zugänglichkeit der primären/sekundären Bedienelemente etc.) und müssen bedienbar sein, ohne dabei die Fahrzeugführung zu gefährden (Auslegung anhand der Handreichweite - vgl. ISO 3958, Lesbarkeit - vgl. DIN EN ISO 15008 etc.).
  Automatisierte Fahrzeugführung: Sofern eine manuelle Fahrzeugführung realisiert werden soll, müssen die Anzeige- und Bedienelemente so ausgelegt, gestaltet und positioniert sein, dass diese manuelle Fahrzeugfügung im nicht automatisierten Betriebszustand ermöglicht werden kann. Sofern ein Eingriff in die Automation während des automatisierten Betriebszustands gesetzlich vorgeschrieben oder aus anderen Gründen gewünscht ist, darf die Zugänglichkeit zu den primären/sekundären Bedienteilen nicht behindert werden. Gesetzlich vorgeschriebene Anzeigen dürfen durch das System nicht verdeckt/behindert werden.
- Urheber: Tobias Oetermann
- Verantwortlichkeit: IKA, Cerence, CanControls, Charamel, Saint Gobain

### R37
Ausreichende Zeitspanne visuell dargestellter Informationen
- Aktiv: true
- Art der Anforderung: Festanaforderung
- Ursprung / Begründung der Anforderung: Benutzbarkeit
- Quelle: DIN EN ISO 15005
- Bemerkung: Visuell dargestellte Informationen des Systems sollten über ein ausreichend langes Zeitintervall bzw. über die Dauer des auslösenden Zustands (bspw. Verkehrssituation) angezeigt werden.
- Urheber: Tobias Oetermann
- Verantwortlichkeit: IKA, Saint Gobain, Charamel

### R38
Konsistenz der dargestellten Informationen und Dialoge
- Aktiv: true
- Art der Anforderung: Festanaforderung
- Ursprung / Begründung der Anforderung: Benutzbarkeit
- Quelle: DIN EN ISO 15005
- Bemerkung: Die Informationsdarstellung und die Dialoge müssen hinsichtlich
  
  • Modus
  • Ort
  • Ausrichtung
  • Dialogmanagement
  
  konsistent sein.
- Urheber: Tobias Oetermann
- Verantwortlichkeit: IKA, DFKI, Cerence, CanControls, Charamel, Saint Gobain

### R39
Angemessenheit der dargestellten Informationen und Dialoge
- Aktiv: true
- Art der Anforderung: Festanaforderung
- Ursprung / Begründung der Anforderung: Benutzbarkeit
- Quelle: DIN EN ISO 15005
- Bemerkung: Die durch das System dargestellten Informationen und/oder Dialoge sollten entsprechend ihres Inhalts und ihrer Merkmale angemessen dargestellt werden (bspw. über die Farbe der Meldung).
- Urheber: Tobias Oetermann
- Verantwortlichkeit: IKA, DFKI, Cerence, CanControls, Charamel, Saint Gobain

### R40
Abbrechbarkeit der Interaktion mit dem System
- Aktiv: true
- Art der Anforderung: Festanaforderung
- Ursprung / Begründung der Anforderung: Nutzbarkeit
- Quelle: DIN EN ISO 15005
- Bemerkung: Die Interaktionen mit dem System (nutzer- oder systemintendiert) müssen zu jedem Zeitpunkt der Interaktion abbrechbar sein. In diesem Fall kehrt das System in einen vordefinierten Systemzustand zurück.
  Relevante Ausnahme: Die Interaktion/der Dialog ist juristisch vorgeschrieben oder wird durch den Hersteller/Entwickler als obligatorisch erachtet.
- Urheber: Tobias Oetermann
- Verantwortlichkeit: IKA, Cerence, DFKI, Charamel, Saint Gobain

### R41
Steuerbarkeit des systemischen Informationsflusses
- Aktiv: true
- Art der Anforderung: Festanaforderung
- Ursprung / Begründung der Anforderung: Nutzbarkeit
- Quelle: DIN EN ISO 15005
- Bemerkung: Die durch das System bereitgestellten Informationen können durch den Nutzer beeinflusst werden können (bspw. Anfordern der Wiederholung einer akustischen Information, Mitteilungszentrale einer visuellen Information etc.)
  Relevante Ausnahme: Juristisch relevante/erforderliche oder mit dem aktuellen Verkehrsgeschehen in Zusammenhang stehende Informationen/Meldungen.
- Urheber: Tobias Oetermann
- Verantwortlichkeit: IKA, Cerence, DFKI, Charamel, Saint Gobain

### R42
Eindeutigkeit der erforderlichen Interaktion
- Aktiv: true
- Art der Anforderung: Festanaforderung
- Ursprung / Begründung der Anforderung: Benutzbarkeit
- Quelle: DIN EN ISO 15005
- Bemerkung: Der Nutzer sollte zu jedem Zeitpunkt unmissverständlich informiert sein, welche Eingabe notwendig ist, um ein angestrebtes Ziel zu erreichen.
- Urheber: Tobias Oetermann
- Verantwortlichkeit: IKA

### R43
Berücksichtigung der potenziellen Nutzer und ihrer Fähigkeiten
- Aktiv: true
- Art der Anforderung: Festanaforderung
- Ursprung / Begründung der Anforderung: Benutzbarkeit
- Quelle: DIN EN ISO 15005
- Bemerkung: Anzeigen und Bedienelemente des Systems sollten inhaltlich und stilistisch so gestaltet werden, dass sie von der vorgesehenen und wahrscheinlichsten Nutzerzielgruppe verstanden werden und angemessene Reaktionen auslösen.
- Urheber: Tobias Oetermann
- Verantwortlichkeit: IKA, DFKI, Cerence, CanControls, Charamel, Saint Gobain

### R44
Angemessenheit und Einfachheit der systemischen Dialoge unter Berücksichtigung der potenziellen Nutzer und ihrer Fähigkeiten
- Aktiv: true
- Art der Anforderung: Festanaforderung
- Ursprung / Begründung der Anforderung: Benutzbarkeit
- Quelle: DIN EN ISO 15005
- Bemerkung: Vokabular und Syntax der durch das System dargestellten Informationen/Dialoge müssen konsistent und einfach sein. Das System nutzt anerkannte Symbole, Abkürzungen und Erwartungen der vorgesehenen und wahrscheinlichsten Nutzerzielgruppe und formuliert die Informationen/Dialoge in einer Form, welche wahrscheinlich von der vorgesehenen und wahrscheinlichsten Nutzerzielgruppe verstanden wird.
- Urheber: Tobias Oetermann
- Verantwortlichkeit: IKA, Cerence, DFKI, Charamel, Saint Gobain

### R45
Bewertung der Nutzereingabe unter Berücksichtigung der aktuellen Gegebenheit
- Aktiv: true
- Art der Anforderung: Festanaforderung
- Ursprung / Begründung der Anforderung: Nutzbarkeit
- Quelle: DIN EN ISO 15005
- Bemerkung: Das System sollte die Möglichkeit haben, fehlerhafte Eingaben des Nutzers unter Berücksichtigung der aktuellen Gegebenheiten zu bewerten und bei offensichtlichen Abweichungen, eine Bestätigung der Eingabe fordern (bspw. Eingabe bei indirekter Fahrzeugführung durch aktuelles Verkehrsgeschehen nicht abbildbar).
- Urheber: Tobias Oetermann
- Verantwortlichkeit: IKA, DFKI, Cerence, CanControls, Charamel, Saint Gobain

### R46
Unterstützung bei der Korrektur fehlerhafter Nutzereingaben
- Aktiv: true
- Art der Anforderung: Festanaforderung
- Ursprung / Begründung der Anforderung: Nutzbarkeit
- Quelle: DIN EN ISO 15005
- Bemerkung: Im Falle fehlerhafter Nutzereingaben (bspw. Eingabe bei indirekter Fahrzeugführung durch aktuelles Verkehrsgeschehen nicht abbildbar) wird der Nutzer bei der Erreichung des beabsichtigten Ziels unterstützt (bspw. indem Alternativen mit gleichem oder ähnlichem Ziel angeboten werden).
- Urheber: Tobias Oetermann
- Verantwortlichkeit: IKA

### R47
Systemstabilität
- Aktiv: true
- Art der Anforderung: Festanaforderung
- Ursprung / Begründung der Anforderung: Nutzbarkeit
- Quelle: DIN EN ISO 15005
- Bemerkung: Es ist nicht möglich, das System über eine Nutzereingabe in einen undefinierten Systemzustand zu bringen und somit zu einem Ausfall des Systems zu führen.
- Urheber: Tobias Oetermann
- Verantwortlichkeit: IKA, Cerence, CanControls, Charamel, Saint Gobain

### R48
Erlernbarkeit und Intuitivität des Systems
- Aktiv: true
- Art der Anforderung: Festanaforderung
- Ursprung / Begründung der Anforderung: Nutzbarkeit
- Quelle: DIN EN ISO 15005
- Bemerkung: Der Umgang mit dem System ist intuitiv und leicht zu gestalten. Der Nutzer sollte für den Prozess des Erlernens des Umgangs mit dem System durch Strategien (bspw. Lernen anhand von Beispielen etc.) unterstützt werden. Ist die Nutzerschnittstelle komplex zu erlernen, sollten weiterführende Hilfestellungen zur Verfügung gestellt werden.
- Urheber: Tobias Oetermann
- Verantwortlichkeit: IKA, Cerence, DFKI, Charamel, Saint Gobain
- Link -> R135

### R49
Strukturierung des Systems
- Aktiv: true
- Art der Anforderung: Festanaforderung
- Ursprung / Begründung der Anforderung: Benutzbarkeit
- Quelle: DIN EN ISO 15005
- Bemerkung: Die Funktionalitäten des Systems sind in sinnvollen Einheiten kombiniert und strukturiert, welche sich nicht ausschließlich nach der erwarteten Nutzungshäufigkeit richten. Auf diese Weise wird der Nutzer dabei unterstützt, neue Funktionalitäten des Systems kennen zu lernen.
- Urheber: Tobias Oetermann
- Verantwortlichkeit: IKA, Cerence, CanControls, Charamel, Saint Gobain

## R50
Übereinstimmung mit dem Standard ISO 4040 - Positionen von Handsteuerungen, Anzeigen und Warnlampen in Motorfahrzeugen
- Aktiv: true
- Quelle: ISO 4040
- Ursprung / Begründung der Anforderung: Zulassungsfähigkeit
- Urheber: Tobias Oetermann
- Art der Anforderung: Festanaforderung

### R51
Uneingeschränkte Sichtbarkeit der Geschwindigkeitsanzeige
- Aktiv: true
- Art der Anforderung: Festanaforderung
- Ursprung / Begründung der Anforderung: Zulassungsfähigkeit
- Quelle: ISO 4040
- Bemerkung: Das aktuell gefahrene Geschwindigkeit des Fahrzeugs muss zu jedem Zeitpunkt des Systembetriebs angezeigt werden. Es darf dabei nicht notwendig sein, dass der Fahrer den Kopf bewegt, um die aktuelle Fahrgeschwindigkeit kontrollieren zu können. Sie sollte somit zu jedem Zeitpunkt ungehindert im direkten Sichtfeld des Fahrers liegen.
- Urheber: Tobias Oetermann
- Verantwortlichkeit: IKA, Cerence, CanControls, Charamel, Saint Gobain

### R52
Uneingeschränkte Sichtbarkeit der Kraftstoff- bzw Energiereserve
- Aktiv: true
- Art der Anforderung: Festanaforderung
- Ursprung / Begründung der Anforderung: Zulassungsfähigkeit
- Quelle: ISO 4040
- Bemerkung: Eine Anzeige für den Anteil der verfügbaren Antriebsenergie in Bezug zu der maximal speicherbaren Menge an Antriebsenergie muss zu jedem Zeitpunkt ersichtlich sein. Darüber hinaus muss aus der Anzeige (oder einer zusätzlichen Anzeige) hervorgehen, wenn weniger als 25% der maximalen Antriebsenergie verbleibt Beide Anzeigen. Es darf dabei nicht notwendig sein, dass der Fahrer den Kopf bewegt, um die Anzeigen kontrollieren zu können. Sie sollten somit zu jedem Zeitpunkt ungehindert im direkten Sichtfeld des Fahrers liegen.
- Urheber: Tobias Oetermann
- Verantwortlichkeit: IKA, Cerence, CanControls, Charamel, Saint Gobain

### R53
Uneingeschränkte Sichtbarkeit der Indikatoren zum Betriebszustand
- Aktiv: true
- Art der Anforderung: Festanaforderung
- Ursprung / Begründung der Anforderung: Zulassungsfähigkeit
- Quelle: ISO 4040
- Bemerkung: Folgende Indikatoren zum Motorbetriebszustand müssen zu jedem Zeitpunkt des Systembetriebs angezeigt werden. Es darf dabei nicht notwendig sein, dass der Fahrer den Kopf bewegt, um den Stand der Indikatoren kontrollieren zu können. Sie sollten somit zu jedem Zeitpunkt ungehindert im direkten Sichtfeld des Fahrers liegen.
  • Motoröldruck (sofern vorhanden)
  • Motorkühlwassertemperatur (sofern vorhanden)
- Urheber: Tobias Oetermann
- Verantwortlichkeit: IKA, Cerence, CanControls, Charamel, Saint Gobain

### R54
Uneingeschränkte Sichtbarkeit der Warnhinweise und sonstiger Hinweise
- Aktiv: true
- Art der Anforderung: Festanaforderung
- Ursprung / Begründung der Anforderung: Zulassungsfähigkeit
- Quelle: ISO 4040
- Bemerkung: Folgende Warnhinweise bzw. sonstigen Hinweise müssen als Kontrollleuchten im direkten Sichtfeld des Fahrers platziert sein. Es darf dabei nicht notwendig sein, dass der Fahrer den Kopf bewegt, um den Status der Kontrollleuchte (An/Aus) kontrollieren zu können. Sie sollten somit zu jedem Zeitpunkt ungehindert im direkten Sichtfeld des Fahrers liegen.
  • Bremse
  • Feststellbremse
  • Fern-/Fernlicht
  • Blinker
  • Fahrtrichtungsanzeiger
  • Sicherheitsgurt-Warnung
  • Anzeige der passiven Rückhalteeinrichtung (nur Fahrer)
  • Motoröldruck
  • Motorkühlmitteltemperatur
  • Kraftstoffstand
  • Batterieladung
  • Automatikgetriebe (wenn an der Instrumententafel oder Lenksäule montiert)
- Urheber: Tobias Oetermann
- Verantwortlichkeit: IKA, Cerence, CanControls, Charamel, Saint Gobain

## R55
Übereinstimmung mit dem Standard DIN EN ISO 15006 - Anforderungen und Konformitätsverfahren für die Ausgabe auditiver Informationen im Fahrzeug
- Aktiv: true
- Art der Anforderung: Festanaforderung
- Quelle: EN ISO 15006
- Urheber: Tobias Oetermann

### R56
Konformes Frequenzspektrum akustischer Signale des Systems
- Aktiv: true
- Art der Anforderung: Festanaforderung
- Quelle: EN ISO 15006
- Ursprung / Begründung der Anforderung: Benutzbarkeit
- Bemerkung: Der empfohlene Frequenzbereich liegt für: 
  • Sprachsignale: 200 - 8000 Hz
  • Tonsignale: 400-2000 Hz (Hauptkomponente des hörbaren Frequenzbereichs)
- Urheber: Tobias Oetermann
- Verantwortlichkeit: Cerence

### R57
Signalorientierung bzw. Aufmerksamkeitserregung des Fahrers durch gezielte Signalauswahl
- Aktiv: true
- Art der Anforderung: Festanaforderung
- Quelle: EN ISO 15006
- Ursprung / Begründung der Anforderung: Nutzbarkeit
- Bemerkung: Um die Signalorientierung bzw. die Aufmerksamkeit des Fahrers zu erhöhen, sollten Breitbandsignale oder Mischungen aus Schmalbandsignalen mit festgelegten Mittenfrequenzen genutzt werden.
- Urheber: Tobias Oetermann
- Verantwortlichkeit: Cerence

### R58
Maximale Hörbarkeit des Signalpegels einer auditiven Information des Systems
- Aktiv: true
- Art der Anforderung: Festanaforderung
- Quelle: EN ISO 15006
- Ursprung / Begründung der Anforderung: Benutzbarkeit
- Bemerkung: Die Hörbarkeit von Signalen des Systems im Fahrzeug sollte maximal sein, wobei zu beachten ist, dass zu hohe Signalpegel eine defensive Reaktion der Nutzer oder Hörschädigungen hervorrufen können. Die hörbaren Signale des Systems sollten dabei unter allen Umgebungsbedingungen wahrnehmbar sein. Mindesthörbarkeit in einer geräuschvollen Umgebung: Der Signal-zu-Umgebung Abstand eines spezifischen Lautheitsspektrums der Hauptkomponente eines Tonsignals muss größer als 1,3 sein.
  Berechnung des Signal-zu-Umgebung Abstand 
  a) Berechne das Schmalband Spektrum des auditiven Signals um die korrespondierende Frequenz zu ermitteln (z. B. die Hauptkomponente eines Tonsignals).
  b) Berechne das spezifische Lautheitsspektrum des auditiven Signals während der Einschaltdauer nach DIN 45631. Dabei muss sichergestellt sein, dass keine Umgebungsgeräusche vorhanden sind (d. h. im stehenden Fahrzeug).
  c) Berechne das spezifische Lautheitsspektrum der Umgebungsgeräusche nach DIN 45631. Das Umgebungsgeräusch muss in der gewünschten Umgebung gemessen werden (z. B. Geschwindigkeit, Straßenoberfläche, Audio System, Fensterposition, usw.).
  d) Berechne den Signal-zu-Umgebung Störabstand des spezifischen Lautheitsspektrums mit der gewünschten Frequenz.
- Urheber: Tobias Oetermann
- Verantwortlichkeit: Cerence

### R59
Vermeidung unangemessener Geräuschpegel
- Aktiv: true
- Art der Anforderung: Festanaforderung
- Quelle: EN ISO 15006
- Ursprung / Begründung der Anforderung: Benutzbarkeit
- Bemerkung: Ein Geräuschpegel gilt in folgenden Fällen als unangemessen und ist somit zu vermeiden:
  • Geräuschpegel ist zu hoch
  • Geräuschpegel ist unerwartet
  • Geräuschpegel ist unbekannt
  • Lautstärkeanstieg ist zu schnell
  Ist eine Vermeidung nicht möglich, sollten zur Vermeidung von Abwehrreaktionen der Nutzer Vorkehrungen getroffen werden (bspw. Erläuterungen etc).
- Urheber: Tobias Oetermann
- Verantwortlichkeit: Cerence

### R60
Lautstärkeanstieg für Warnsignale
- Aktiv: true
- Art der Anforderung: Festanaforderung
- Quelle: EN ISO 15006
- Ursprung / Begründung der Anforderung: Nutzbarkeit
- Soll-Zahlenwert: max 30 ms
- Bemerkung: Der Lautstärkeanstieg auf maximale Lautstärke sollte bei Warnsignalen in kurzer Zeit erfolgen.
- Urheber: Tobias Oetermann
- Verantwortlichkeit: Cerence

### R61
Terminierung  auditiver Signale in Abhängigkeit der erwarteten/notwendigen Nutzerreaktion
- Aktiv: true
- Art der Anforderung: Festanaforderung
- Quelle: EN ISO 15006
- Ursprung / Begründung der Anforderung: Nutzbarkeit
- Bemerkung: In Abhängigkeit der Semantik der auditiven Information bzw. des Signals wird unter Umständen eine mehr oder weniger zeitrelevante Reaktion des Nutzers notwendig. Die Terminierung der auditiven Mitteilung richtet sich dabei nach der zeitlichen Relevanz der Reaktion:
  • kurzfristige Reaktion (zeitkritisch - nicht zwingend sicherheitskritisch): unverzüglich nach nach Erkennen der Notwenigkeit der Mitteilung
  • mittelfristige Reaktion: unverzüglich oder bis 10 s verzögert.
  • langfristige Reaktion: unverzüglich (sofern keine konkurrierenden Mitteilungen höherer Priorität vorliegen) oder verzögert
- Urheber: Tobias Oetermann
- Verantwortlichkeit: Cerence

### R62
Einfachheit und Konsistenz sprachcodierter auditiver Mitteilungen
- Aktiv: true
- Art der Anforderung: Festanaforderung
- Quelle: EN ISO 15006
- Ursprung / Begründung der Anforderung: Benutzbarkeit
- Bemerkung: Sprachcodierte Systemmitteilungen sollten ein einheitliches und einfaches Vokabular verwenden und zum geschriebenen Text in jeder Anwendung des Systems konsistent sein.
- Urheber: Tobias Oetermann
- Verantwortlichkeit: Cerence

### R63
Maximum der Informationseinheiten sprachcodierter auditiver Mitteilungen
- Aktiv: true
- Art der Anforderung: Festanaforderung
- Quelle: EN ISO 15006
- Ursprung / Begründung der Anforderung: Benutzbarkeit
- Soll-Zahlenwert: max 5 Informations-
  einheiten
- Bemerkung: Sprachcodierte Systemmitteilungen sollten in der Anzahl ihrer Informationseinheiten  Informationseinheiten begrenzt sein, um die Beanspruchung der Aufmerksamkeit und des Kurzzeitgedächtnisses der Nutzer zusammen mit weiteren Einschränkungen der menschlichen Informationsverarbeitung gerecht zu werden. Darüber hinaus ist die Zeitspanne einer vollständigen Nachricht in Hinblick auf die Zeitkritikalität der notwendigen bzw. erwarteten Reaktion des Nutzers zu begrenzen.
- Urheber: Tobias Oetermann
- Verantwortlichkeit: Cerence

### R64
Unterstützende Mechanismen zum Verständnis komplexer sprachcodierter auditiver Mitteilungen
- Aktiv: true
- Art der Anforderung: Festanaforderung
- Quelle: EN ISO 15006
- Ursprung / Begründung der Anforderung: Benutzbarkeit
- Bemerkung: Um den Nutzer bei dem Verständnis und bezüglich der Handlungsableitung von komplexen sprachcodierten auditiven Systemmitteilungen zu unterstützen,gibt es verschiedene Methoden, welche in Kombination oder einzeln verwendet werden können/sollten:
  • Anordnung der Informationseinheiten bezüglich ihrerpotenziellen Relevanz
  • Anordnungen handlungsbezogene Informationseinheiten am Ende der Meldung
  • Einsatz von Schlüsselbegriffen, Sprachmelodie und Betonung
  • Einsatz redundanter visueller Anzeigen – zumindest für die wichtigsten Informationseinheiten
  • Bereitstellung von Mechanismen für die optionale Wiederholung von Meldungen
  • Bereitstellung von Mechanismen um Sprachmeldungen zu stoppen
- Urheber: Tobias Oetermann
- Verantwortlichkeit: Cerence

### R65
Redundanz sicherheitsrelevanter auditiver Mitteilungen
- Aktiv: true
- Art der Anforderung: Festanaforderung
- Quelle: EN ISO 15006
- Ursprung / Begründung der Anforderung: Nutzbarkeit
- Bemerkung: Sicherheitsrelevante Informationen, welche eine unverzügliche Handlung seitens des Nutzers bedingen, dürfen nicht ausschließlich auditiv erfolgen, sondern müssen auch über andere Sinneskanäle (visuell, haptisch, kinästhetisch) vermittelt werden.
- Urheber: Tobias Oetermann
- Verantwortlichkeit: Cerence, Saint Gobain, IKA, Charamel

## R66
Übereinstimmung mit dem Standard ISO 2575 - Symbole für Bedienteile, Anzeigen und Warnleuchten (Publikation im Mai)
- Aktiv: true
- Art der Anforderung: Festanaforderung
- Quelle: ISO 2575
- Ursprung / Begründung der Anforderung: Wiedererkennbarkeit
- Urheber: Tobias Oetermann

### R67
Nutzung standardisierter Symbole zur Steigerung des Verständnis der zu übermittelnden Information
- Aktiv: true
- Art der Anforderung: Festanaforderung
- Quelle: ISO 2575
- Ursprung / Begründung der Anforderung: Wiedererkennbarkeit
- Bemerkung: Um eine hohe Wiedererkennbarkeit und damit verbunden eine hohe Intuitivität bezüglich der Bedienteile, Anzeigen und Warnleuchten des Systems zu gewährleisten sind die in den Anhängen der ISO DIS 2575 beschriebenen Symbole zu nutzen. Dabei sind die Symbolparameter wie Liniendicke, Lücken zwischen Linien, Symbol- und Pfeilformen etc. begründet gewählt, um die Lesbarkeit der Symbole zu optimieren. Es darf daher nur aus folgenden Gründen von den Parametern abgewichen werden:
  • Technische Einschränkungen (Display) machen eine Modifikation der Liniendicke (oder anderer Parameter) notwendig
  • Optische Anpassungen (Design) sind in geringfügigem Ausmaß akzeptabel (Linienstärke oder Abrundung an den Ecken etc.), um dem Design des Systems zu entsprechen oder die Wahrnehmbarkeit zu erhöhen
  • Wenn nicht anders durch die Symbolbeschreibung festgelegt, kann ein Symbol entweder in Umriss- oder Vollform dargestellt werden
  • Symbole zur Darstellung von Fahrzeugen, Sitzen und Lenkrädern können in Hinblick auf eine spezifische Repräsentation modifiziert werden
- Urheber: Tobias Oetermann
- Verantwortlichkeit: Charamel, IKA, Saint Gobain
- Link -> R68

### R68
Nutzung standardisierter Farben für Symbole zur Steigerung des Verständnis der zu übermittelnden Information
- Aktiv: true
- Art der Anforderung: Festanaforderung
- Quelle: ISO 2575
- Ursprung / Begründung der Anforderung: Wiedererkennbarkeit
- Bemerkung: Die in Anforderung 55 standardisierten Symbole zur Steigerung der Intuitivität der Bedienteile, Anzeigen und Warnleuchten des Systems sind in spezifischen Fragen anzuwenden. Dabei gilt im Besonderen der folgende Farbcode:
  • Rot: Gefahr für Personen oder sehr ernste Schäden an Geräten, unmittelbar oder unmittelbar bevorstehend
  • Gelb: Vorsicht, außerhalb der normalen Betriebsgrenzen, Fehlfunktion des Fahrzeugsystems, Beschädigung des Fahrzeugs wahrscheinlich, oder ein anderer Zustand, der längerfristig eine Gefahr darstellen kann
  • Grün: sicherer, normaler Betriebszustand
- Urheber: Tobias Oetermann
- Verantwortlichkeit: IKA, Saint Gobain, Charamel
- Link -> R226

## R69
Übereinstimmung mit dem Standard DIN ISO 7000 - Graphische Symbole auf Einrichtungen - Index und Übersicht
- Aktiv: true
- Art der Anforderung: Festanaforderung
- Quelle: ISO 7000
- Ursprung / Begründung der Anforderung: Wiedererkennbarkeit
- Urheber: Tobias Oetermann

### R70
Nutzung standardisierter Symbole zur Steigerung des Verständnis der zu übermittelnden Information
- Aktiv: true
- Art der Anforderung: Festanaforderung
- Quelle: ISO 7000
- Ursprung / Begründung der Anforderung: Wiedererkennbarkeit
- Bemerkung: Um eine hohe Wiedererkennbarkeit und damit verbunden eine hohe Intuitivität bezüglich der Bedienteile, Anzeigen und Warnleuchten des Systems zu gewährleisten sind die in den Anhängen der DIN ISO 7000 beschriebenen Symbole zu nutzen.
- Urheber: Tobias Oetermann
- Verantwortlichkeit: IKA, Saint Gobain, Charamel

## R71
Übereinstimmung mit ESOP - European Statement of Principles (Europäischen Grundsatzkatalogs zur Mensch-Maschine-Schnittstelle)
- Aktiv: true
- Art der Anforderung: Festanaforderung
- Quelle: ESOP
- Urheber: Tobias Oetermann

### R72
Gesamtdesign
- Aktiv: true
- Art der Anforderung: Festanaforderung
- Quelle: ESOP
- Urheber: Tobias Oetermann
- Verantwortlichkeit: IKA, DFKI, Cerence, CanControls, Charamel, Saint Gobain

#### R73
Unterstützung
- Aktiv: true
- Art der Anforderung: Festanaforderung
- Ursprung / Begründung der Anforderung: Gesamtdesign
- Quelle: ESOP
- Bemerkung: Das System ist so zu gestalten, dass es den Fahrer unterstützt. 
  Automatisierte Fahrzeugführung: Dem Fahrer/Passagier werden notwendige Informationen angezeigt, um über den aktuellen Automationszustand informiert zu sein.
- Urheber: Tobias Oetermann
- Verantwortlichkeit: IKA, DFKI, Cerence, CanControls, Charamel, Saint Gobain

#### R74
Vermeidung gefährlichen Verhaltens
- Aktiv: true
- Art der Anforderung: Festanaforderung
- Ursprung / Begründung der Anforderung: Gesamtdesign
- Quelle: ESOP
- Bemerkung: Das System ist so zu gestalten, dass es nicht zu einem potenziell gefährdenden Verhalten des Fahrers oder anderer Verkehrsteilnehmer Anlass gibt. 
  Automatisierte Fahrzeugführung: Ein Eingriff des Nutzers soll möglichst verhindert werden.
- Urheber: Tobias Oetermann
- Verantwortlichkeit: IKA, DFKI, Cerence, CanControls, Charamel, Saint Gobain

#### R75
Angemessenheit der kognitiven Belastung
- Aktiv: true
- Art der Anforderung: Festanaforderung
- Ursprung / Begründung der Anforderung: Gesamtdesign
- Quelle: ESOP
- Bemerkung: Der Fahrer hat begrenzte kognitive Ressourcen, welche er jedoch in der Lage ist, nach eigenem Ermessen zu verteilen. Das System muss dabei mit dem Aufmerksamkeitsbedarf der jeweiligen Fahrsituation vereinbar sein. 
  Automatisierte Fahrzeugführung: Wenn Aufmerksamkeit benötigt wird (werden sollte), kann das System die Aufmerksamkeit entsprechend leiten/verteilen
- Urheber: Tobias Oetermann
- Verantwortlichkeit: IKA, DFKI, Cerence, CanControls, Charamel, Saint Gobain

#### R76
Ablenkungsvermeidung
- Aktiv: true
- Art der Anforderung: Festanaforderung
- Ursprung / Begründung der Anforderung: Gesamtdesign
- Quelle: ESOP
- Bemerkung: Das System soll nicht ablenken und nicht der Unterhaltung des Nutzers dienen, sondern ihn in seiner Fahraufgabe unterstützen. 
  Automatisierte Fahrzeugführung: Das System soll vor allem in der Stärkung des Vertrauenszustandes unterstützen und dem Fahrer über eine geeignete Anzeige wesentliche Informationen über den aktuellen Automationszustand zur Verfügung stellen, um ein Verständnis für die aktuelle Fahrsituation zu schaffen.
  (Unterstützt durch DIN EN ISO 15005 - Absatz 5.2.3.2.2)
- Urheber: Tobias Oetermann
- Verantwortlichkeit: IKA, DFKI, Cerence, CanControls, Charamel, Saint Gobain

#### R77
Vermeidung gefährlichen Verhaltens
- Aktiv: true
- Art der Anforderung: Festanaforderung
- Ursprung / Begründung der Anforderung: Gesamtdesign
- Quelle: ESOP
- Bemerkung: Die angezeigten Informationen dürfen kein gefährliches Verhalten des Fahrers provozieren oder bestärken.
  Automatisierte Fahrzeugführung: Die angezeigten Informationen sollten den Fahrer/Nutzer nicht zu einem (potenziell gefährlichen) Eingriff in die Fahrzeugführung verleiten, solange diese aus technischer Sicht nicht notwendig ist.
- Urheber: Tobias Oetermann
- Verantwortlichkeit: Charamel, Saint Gobain, IKA, Cerence

#### R78
Einheitlichkeit
- Aktiv: true
- Art der Anforderung: Festanaforderung
- Ursprung / Begründung der Anforderung: Gesamtdesign
- Quelle: ESOP
- Bemerkung: Bei der Entwicklung des Systems ist auf ein grundlegendes Maß an Einheitlichkeit zu achten, um ein positives Nutzungserlebnis zu generieren. Dies bezieht sich insbesondere auf eine einheitliche Verwendung von
  • Begrifflichkeiten
  • Symbolen und/oder Ausdrücken zur Darstellung von Informationen
  • Farben, Symbolen, akustischen Signalen, Beschriftungen
  • physischen Interaktionsformen und funktionsbezogenen Rückmeldungen
  (Unterstützt durch DIN EN ISO 15005 - Absatz 5.2.3.2.1)
- Urheber: Tobias Oetermann
- Verantwortlichkeit: Saint Gobain, IKA, Charamel, Cerence

### R79
Installation
- Aktiv: true
- Art der Anforderung: Festanaforderung
- Quelle: ESOP
- Urheber: Tobias Oetermann

#### R80
Sichere Montage
- Art der Anforderung: Festanaforderung
- Aktiv: true
- Ursprung / Begründung der Anforderung: Installation
- Quelle: ESOP
- Bemerkung: Die entwickelten Systeme sind speziell in Hinblick auf die passive Sicherheit sachgemäß im Fahrzeug zu verbauen. Es kommen folgende Möglichkeiten in Betracht:
  • Festeinbau
  • Einbau zur beweglichen Verwendung innerhalb eines bestimmten Raumes
  • Einbau in eine Halterung
- Urheber: Tobias Oetermann
- Verantwortlichkeit: IKA, Cerence, CanControls, Charamel, Saint Gobain
- Link -> R172

#### R258
Uneingeschränktes Fahrer-Sichtfeld
- Aktiv: true
- Art der Anforderung: Festanaforderung
- Quelle: ESOP
- Ursprung / Begründung der Anforderung: Installation
- Bemerkung: Das Sichtfeld des Fahrers nach Draußen (unmittelbar durch die Windschutzscheibe sowie unmittelbar und mittelbar durch die Seitenfenster und die Heckscheibe) stellt unabdingbare Mindestanforderung dar (vgl. ECE-R125) und darf durch Systeme nicht behindert werden. Auf direkt im Sichtfeld befindliche Anzeigen (HUD) kann dieser Grundsatz nur bedingt angewendet werden.
  Automatisierte Fahrzeugführung: Die Anzeigen in der Windschutzscheibe müssen den aktuellen Rechtsvorschriften entsprechen.
- Urheber: Tobias Oetermann
- Verantwortlichkeit: IKA, Cerence, CanControls, Charamel, Saint Gobain
- Link -> R259

#### R81
Vermeidung von Sichtverdeckungen
- Aktiv: true
- Art der Anforderung: Festanaforderung
- Ursprung / Begründung der Anforderung: Installation
- Quelle: ESOP
- Bemerkung: Das System sollte Anzeigen nicht behindern bzw. verdecken, welche der primären Aufgabe des Fahrers, der Fahrzeugführung, dienen.
  Automatisierte Fahrzeugführung: Zu definierende Anzeigen, welche der Sicherheit des automatisierten Fahrzustandes (Zeit bis zur Übernahme, Entscheidungsfindung etc.) dienen (können), sowie solche, die juristisch vorgeschrieben sind, dürfen nicht verdeckt oder behindert werden.
- Urheber: Tobias Oetermann
- Verantwortlichkeit: IKA, Cerence, CanControls, Charamel, Saint Gobain

#### R82
Zugänglichkeit zu Bedienteilen
- Aktiv: true
- Art der Anforderung: Festanaforderung
- Ursprung / Begründung der Anforderung: Installation
- Quelle: ESOP
- Bemerkung: Das System soll den Zugang zu Bedienteilen, welche der primären Aufgabe des Fahrers, der Fahrzeugführung, dienen, nicht behindert.
  Automatisierte Fahrzeugführung: Bedienteile, welche der Aktivierung bzw. Deaktivierung der automatisierten Fahrzeugführung dienen, dürfen nicht durch weitere Bedienteile behindert werden. Sofern ein Eingriff in die Automation gesetzlich vorgeschrieben oder aus anderen Gründen gewünscht ist, darf die Zugänglichkeit zu dem primären Stellteilen (aktuell: Pedalerie und Lenkrad) nicht behindert werden. Juristisch vorgeschriebene Bedienteile dürfen nicht behindert werden.
- Urheber: Tobias Oetermann
- Verantwortlichkeit: IKA, Cerence, CanControls, Charamel, Saint Gobain

#### R83
Orientierung an Sichtlinie
- Aktiv: true
- Art der Anforderung: Festanaforderung
- Ursprung / Begründung der Anforderung: Installation
- Quelle: ESOP
- Soll-Zahlenwert: max 30° (eingeschlossener Winkel Sicht - Anzeige)
- Bemerkung: Visuelle Anzeigen sollten so nah wie möglich/praktikabel an der Sichtlinie des Fahrers positioniert werden.
  Automatisierte Fahrzeugführung: In Abhängigkeit des Automationszustands Positionierung relevanter Anzeigen in der direkten Nähe der zu erwartenden Sichtlinie des Nutzers. Alternativ: In Abhängigkeit der aktuellen Sichtlinie (Erfassung der Blickrichtung) Anpassung der visuellen Anzeigen.
- Urheber: Tobias Oetermann
- Verantwortlichkeit: IKA, Cerence, CanControls, Charamel, Saint Gobain
- Link -> R131
- Link -> R116

#### R84
Vermeidung Blendung/Reflexion
- Aktiv: true
- Art der Anforderung: Festanaforderung
- Ursprung / Begründung der Anforderung: Installation
- Quelle: ESOP
- Bemerkung: Visuelle Anzeigen sollten nicht blenden oder reflektieren. Anzeigen sollten manuell oder automatisch in der Helligkeit variierbar sein.
- Urheber: Tobias Oetermann
- Verantwortlichkeit: Saint Gobain, IKA, Charamel

### R85
Darstellung von Information
- Aktiv: true
- Art der Anforderung: Festanaforderung
- Quelle: ESOP
- Urheber: Tobias Oetermann

#### R86
Prägnante Informationsgestaltung
- Aktiv: true
- Art der Anforderung: Festanaforderung
- Ursprung / Begründung der Anforderung: Darstellung von Information
- Quelle: ESOP
- Soll-Zahlenwert: max. 1 s (ESOP), max. 1,5 s (DIN EN ISO 15005); Blickdauer -ESOP; Verweildauer (Fixation & Sakkade) - DIN EN ISO 15005
- Bemerkung: Die visuell angezeigten maßgeblichen Informationen sollten so gestaltet sein, dass sie mit wenigen Blicken in kurzer Zeit unter beschränktem Tätigwerden erfasst werden können.
  (Unterstützt durch DIN EN ISO 15005 - Absatz 5.2.4.2.1)
- Urheber: Tobias Oetermann
- Verantwortlichkeit: Saint Gobain, IKA, Charamel

#### R87
Standardisierung
- Aktiv: true
- Art der Anforderung: Festanaforderung
- Ursprung / Begründung der Anforderung: Darstellung von Information
- Quelle: ESOP
- Bemerkung: Internationale/nationale Normen zu
  • Lesbarkeit
  • Hörbarkeit
  • Begriffen
  • Akronymen
  • Abkürzungen
  • Piktogrammen
  • Symbolen
  sollten berücksichtigt werden.
  (Unterstützt durch DIN EN ISO 15005 - Absatz 5.4.2.2.2)
- Urheber: Tobias Oetermann
- Verantwortlichkeit: IKA, Saint Gobain, Cerence, Charamel

#### R88
Genauigkeit
- Aktiv: true
- Art der Anforderung: Festanaforderung
- Ursprung / Begründung der Anforderung: Darstellung von Information
- Quelle: ESOP
- Bemerkung: Die maßgeblichen Informationen für die Fahrzeugführung sollten eindeutig und genau formuliert sein.
  Automatisierte Fahrzeugführung: Die vorgeschriebenen oder wesentlichen Informationen, welche der Nutzer zum Verständnis des aktuellen Automationszustandes benötigt, sollten genau und eindeutig formuliert/dargestellt sein.
- Urheber: Tobias Oetermann
- Verantwortlichkeit: IKA, Cerence, Charamel, Saint Gobain
- Link -> R120

#### R89
Taktung
- Aktiv: true
- Art der Anforderung: Festanaforderung
- Ursprung / Begründung der Anforderung: Darstellung von Information
- Quelle: ESOP
- Bemerkung: Die Informationsdarstellung der maßgeblichen Informationen für die Fahrzeugführung sollte rechtzeitig erfolgen. 
  Automatisierte Fahrzeugführung: Die vorgeschriebenen oder wesentlichen Informationen, welche der Nutzer zum Verständnis des aktuellen Automationszustandes benötigt, sollten rechtzeitig angezeigt werden.
  (Unterstützt durch DIN EN ISO 15005 - Absatz 5.2.4.3.4)
- Urheber: Tobias Oetermann
- Verantwortlichkeit: IKA, DFKI, Cerence, CanControls, Charamel, Saint Gobain

#### R90
Priorisierung
- Aktiv: true
- Art der Anforderung: Festanaforderung
- Ursprung / Begründung der Anforderung: Darstellung von Information
- Quelle: ESOP
- Bemerkung: Informationen mit einer höheren Sicherheitsrelevanz sollte eine höhere Priorität beigemessen werden. Die Priorisierung der Informationen geschieht mittels des Standards ISO/TS 16951.
  (Unterstützt durch DIN EN ISO 15005 - Absatz 5.2.4.2.4 und 5.2.4.3.3 & DIN EN ISO 15006 Absatz 5.2.2 (akustische Signale))
- Urheber: Tobias Oetermann
- Verantwortlichkeit: IKA, Saint Gobain, Cerence, Charamel

#### R91
Lautstärkeregelung Geräusch/Ton
- Aktiv: true
- Art der Anforderung: Festanaforderung
- Ursprung / Begründung der Anforderung: Darstellung von Information
- Quelle: ESOP
- Bemerkung: Systemische Geräusche/Töne, welche in ihrer Lautstärke nicht durch den Nutzer beeinflusst werden könne, sollten akustische Warnsignale nicht überlagern (Umsetzungsbeispiele: geringere Lautstärke, kurze Zeitspanne, intermittierende Geräusche: längere Unterbrechungsintervalle)
- Urheber: Tobias Oetermann
- Verantwortlichkeit: Cerence

### R92
Interaktion mit Anzeige- und Bedienteilen
- Aktiv: true
- Art der Anforderung: Festanaforderung
- Quelle: ESOP
- Urheber: Tobias Oetermann
- Link -> R140

#### R93
Einhändige Bedienbarkeit
- Aktiv: false
- Art der Anforderung: Festanaforderung
- Ursprung / Begründung der Anforderung: Interaktion mit Anzeige- und Bedienteilen
- Erläuterung für Streichung / Änderung: Da Systeme im (hoch-) automatisierten Kontext entwickelt werden, ist eine Bedienbarkeit mit einer Hand nicht zwingend erforderlich. Aus Gründen der vereinfachten Nutzbarkeit macht die Umsetzung einer einhändigen Bedienbarkeit unter Umständen dennoch Sinn-
- Quelle: ESOP
- Bemerkung: Das System sollte einhändig bedient werden können, damit der Fahrer während der Bedienung immer eine Hand am Lenkrad belassen kann.
  (Unterstützt durch DIN EN ISO 15005 - Abschnitt 5.2.2.2.2)
- Urheber: Tobias Oetermann
- Verantwortlichkeit: IKA, Cerence, CanControls, Charamel, Saint Gobain

#### R94
Unterbrechbarkeit
- Aktiv: true
- Art der Anforderung: Festanaforderung
- Quelle: ESOP
- Ursprung / Begründung der Anforderung: Interaktion mit Anzeige- und Bedienteilen
- Soll-Zahlenwert: max. 1,5 s (Verweildauer (Fixation & Sakkade) pro Interaktionsschritt - DIN EN ISO 15005)
- Bemerkung: Eine systemische Ein-/Ausgabe sollte entweder Unterbrechbar oder nur von kurzer Dauer sein. Während der Unterbrechung sollte die Fahrer Eingabe nur gelöscht werden, wenn eine hinreichend lange Zeit vergangen ist. Auf sprachbasierte Ein-/Ausgaben kann/muss diese Anforderung nicht angewendet werden.
  (Unterstützt durch DIN EN ISO 15005 - Absatz 5.2.4.2.2)
- Urheber: Tobias Oetermann
- Verantwortlichkeit: IKA, Cerence, Charamel, Saint Gobain

#### R95
Fortführbarkeit
- Aktiv: true
- Art der Anforderung: Festanaforderung
- Quelle: ESOP
- Ursprung / Begründung der Anforderung: Interaktion mit Anzeige- und Bedienteilen
- Bemerkung: Die unterbrochene Ein-/Ausgabe sollte an derselben Stelle, an welcher die ein-/Ausgabe zuvor unterbrochen wurde, oder an einem anderen logischen Ort fortgeführt werden können. (DIN EN IST 15005: Gilt auch für systemseitig unterbrochene Interaktionen (bspw. durch Verkehrsdurchsage etc.))
  (Unterstützt durch DIN EN ISO 15005 - Absatz 5.3.3.2.2)
- Urheber: Tobias Oetermann
- Verantwortlichkeit: IKA, Cerence, Charamel, Saint Gobain

#### R96
Geschwindigkeitsregelung (Ein-/Ausgabe)
- Aktiv: true
- Art der Anforderung: Festanaforderung
- Quelle: ESOP
- Ursprung / Begründung der Anforderung: Interaktion mit Anzeige- und Bedienteilen
- Bemerkung: Die Geschwindigkeit, in welcher eine Ein-/Ausgabe erfolgt, sollte vom Nutzer eingestellt werden können. 
  Relevante Ausnahme: Die dargestellte Information hängt direkt mit der unmittelbaren Verkehrssituation zusammen. Das System muss dem Fahrer helfen, Missverständnisse zu vermeiden.
  (Unterstützt durch DIN EN ISO 15005 - Absatz 5.2.4.3.1)
- Urheber: Tobias Oetermann
- Verantwortlichkeit: IKA, Cerence, Charamel, Saint Gobain

#### R97
Vermeidung der Beeinträchtigung primärer Bedienteile
- Aktiv: true
- Art der Anforderung: Festanaforderung
- Quelle: ESOP
- Ursprung / Begründung der Anforderung: Interaktion mit Anzeige- und Bedienteilen
- Bemerkung: Die systemischen Bedienteile sollten die Handhabung der primären Bedienteile nicht beeinträchtigen, sondern unterstützen (bspw. durch Anordnung entsprechend der Nutzungshäufigkeit).
  Automatisierte Fahrzeugführung: Die systemischen Bedienteile dürfen durch ihr Gestaltung (Anordnung, Kinematik, Kraftaufwand, Bedienweg etc.) keine versehentliche Aktivierung/Deaktivierung der automatisierten Fahrfunktion provozieren. Juristisch vorgeschriebene Bedienteile dürfen nicht beeinträchtigt werden.
- Urheber: Tobias Oetermann
- Verantwortlichkeit: IKA

#### R98
Lautstärkeregelung Information
- Aktiv: true
- Art der Anforderung: Festanaforderung
- Quelle: ESOP
- Ursprung / Begründung der Anforderung: Interaktion mit Anzeige- und Bedienteilen
- Bemerkung: Der Nutzer kann die Lautstärke von nicht sicherheitsrelevanten, auditiven Informationen variieren und bis zu einem nicht mehr wahrnehmbaren Maß reduzieren. Eine redundante visuelle Darstellung der Information sollte berücksichtigt werden.
- Urheber: Tobias Oetermann
- Verantwortlichkeit: Cerence

#### R99
Systemreaktion
- Aktiv: true
- Art der Anforderung: Festanaforderung
- Quelle: ESOP
- Ursprung / Begründung der Anforderung: Interaktion mit Anzeige- und Bedienteilen
- Soll-Zahlenwert: max 250 ms (Reaktionszeit)
- Bemerkung: Die Eingabe des Nutzers erzeugt eine zeitnahe und angemessen systemische Reaktion (Rückmeldung, Bestätigung etc.). Die Reaktion erfolgt auf zwei Ebenen:
  1. Rückmeldung nach Betätigung des Bedienteils (z.B. Signalton, haptisches Feedback etc.)
  2. Dialogebene: Reaktion des Systems auf die Eingabe (Inhalt) (z.B. Änderung der Visualisierung etc.)
  Relevante Ausnahme: Sprachgesteuerte Systeme unterliegen nicht zwingend dieser Anforderung, da naturgegeben auch innerhalb eines Satzes längere Pausen entstehen können, welche keine Reaktion hervorrufen sollen.
  (Unterstützt durch DIN EN ISO 15005 - Absatz 5.2.4.2.3)
- Urheber: Tobias Oetermann
- Verantwortlichkeit: IKA, DFKI, Cerence, CanControls, Charamel, Saint Gobain
- Link -> R185

#### R100
Deaktivierbarkeit
- Aktiv: true
- Art der Anforderung: Festanaforderung
- Quelle: ESOP
- Ursprung / Begründung der Anforderung: Interaktion mit Anzeige- und Bedienteilen
- Bemerkung: Nicht sicherheitsrelevante Informationen (visuell) sollten in einen Systemzustand gebracht werden können, in welchem der Nutzer nicht aktiv mit den Informationen konfrontiert wird. (DIN EN ISO 15005: Gilt ebenso für akustische Informationen/Meldungen, welche keinen sicherheitsrelevanten Bezug haben)
  Automatisierte Fahrzeugführung: Die systemischen visuellen Informationen, welchen keinen sicherheitsrelevanten Einfluss auf die Fahrsituation haben (Entscheidung/Reaktionen des Fahrers, vertrauensfördernde Visualisierung zur Eingriffsvermeidung etc.) lassen sich durch den Nutzer deaktivieren.
  (Unterstützt durch DIN EN ISO 15005 - Absatz 5.3.3.3.1)
- Urheber: Tobias Oetermann
- Verantwortlichkeit: IKA, Saint Gobain, Cerence, Charamel

### R101
Systemverhalten
- Aktiv: true
- Art der Anforderung: Festanaforderung
- Quelle: ESOP
- Urheber: Tobias Oetermann

#### R102
Situationsbedingte Visualisierung
- Aktiv: true
- Art der Anforderung: Festanaforderung
- Quelle: ESOP
- Ursprung / Begründung der Anforderung: Systemverhalten
- Bemerkung: Nicht die Fahrzeugführung betreffende visuelle Informationen, welche einem dynamischen und unvorhersehbaren Charakter folgen und deren Geschwindigkeit nicht vom Nutzer beeinflusst werden kann bzw. deren Ausführung nicht vom Nutzer unterbrochen und jederzeit fortgesetzt werden kann, sind während der Fahrt zu deaktivieren, um eine Ablenkung des Nutzers zu vermeiden.
  Automatisierte Fahrzeugführung: Die Systeme, welche während der automatisierten Fahrzeugführung aktiviert sind und der Information oder Unterhaltung des Nutzers dienen, jedoch keinen wesentlichen Beitrag zur Fahrsicherheit bzw. zum Bewusstsein des Nutzers über das aktuelle Verkehrsgeschehen beitragen, sind während der manuellen Fahrzeugführung zu deaktivieren oder in einen unauffälligen Betriebsmodus zu schalten.
- Urheber: Tobias Oetermann
- Verantwortlichkeit: IKA, Charamel, Saint Gobain

#### R103
Vermeidung der systemischen Störung primärer Bedienteile oder Anzeigen
- Aktiv: true
- Art der Anforderung: Festanaforderung
- Quelle: ESOP
- Ursprung / Begründung der Anforderung: Systemverhalten
- Bemerkung: Vorgeschrieben Anzeigen und/oder Bedienteile oder Anzeigen/Bedienteile, welche der Fahrsicherheit dienen, dürfen durch die Funktionalität (auch im Falle einer Fehlfunktion) des Systems nicht gestört/verdeckt/beeinträchtigt werden.
  Automatisierte Fahrzeugführung: Sicherheitsrelevante und/oder gesetzlich vorgeschriebene Anzeigen/Bedienteile (z.B. Aktivierung/Deaktivierung der automatisierten Fahrfunktion, Geschwindigkeitsanzeige) dürfen während der automatisierten Fahrt nicht gestört/behindert/verdeckt werden. Für Anzeigen/Bedienteile, welche nur für die manuelle Fahrzeugführung vorgeschrieben und/oder sicherheitsrelevant sind, muss eine Fehlfunktion des Systems, welche eine Störung/Verdeckung/Beeinträchtigung über die Deaktivierung der automatisierten Fahrfunktion hinaus zur Folge hätte, technisch ausgeschlossen werden.
- Urheber: Tobias Oetermann
- Verantwortlichkeit: IKA, DFKI, Cerence, CanControls, Charamel, Saint Gobain

#### R104
Klarheit/Verantwortlichkeit
- Aktiv: true
- Art der Anforderung: Festanaforderung
- Quelle: ESOP
- Ursprung / Begründung der Anforderung: Systemverhalten
- Bemerkung: Systemfunktionen, welche nicht zur Nutzung während der Fahrt vorgesehen sind, sollten während der Fahrt deaktiviert sein. Alternativ sollte ein deutlicher Hinweis über die nicht erwünschte Interaktion und die Verantwortlichkeit informieren.
  Automatisierte Fahrzeugführung: Systemfunktionen, welche lediglich für die Nutzung während der automatisierten Fahrzeugführung vorgesehen sind, sollten zwingend während der manuellen Fahrzeugführung deaktiviert werden. Der Nutzer wird stetig über die Handlungsfreiheit (juristisch, systemisch) informiert.
  (Unterstützt durch DIN EN ISO 15005 - Abschnitt 5.2.2.2.4 & DIN EN ISO 17287 - Abschnitt 4.2.5.2)
- Urheber: Tobias Oetermann
- Verantwortlichkeit: IKA, DFKI, Cerence, CanControls, Charamel, Saint Gobain

#### R105
Sicherheitsrelevante Information
- Aktiv: true
- Art der Anforderung: Festanaforderung
- Quelle: ESOP
- Ursprung / Begründung der Anforderung: Systemverhalten
- Bemerkung: Dem Nutzer werden Informationen über den aktuellen Systemstatus sowie sämtliche (sicherheitsrelevanten) Systemstörungen zur Verfügung gestellt.
  Automatisierte Fahrzeugführung: Der Nutzer wird zu jedem Zeitpunkt eindeutig und unmissverständlich über den aktuellen Fahrmodus und den Systemzustand informiert. Etwaige Fehlfunktionen sind entsprechend ihrer Dringlichkeit und ihrer sicherheitsrelevanten Auswirkungen darzustellen und Handlungsempfehlungen bzw. -anweisungen entsprechend prägnant und unmissverständlich zu vermitteln.
  (Unterstützt durch DIN EN ISO 15005 - Abschnitt 5.3.2.2.2 & DIN EN ISO 17287 - Abschnitt 4.2.6)
- Urheber: Tobias Oetermann
- Verantwortlichkeit: IKA, DFKI, Cerence, CanControls, Charamel, Saint Gobain

### R106
Informationen zum System
- Aktiv: true
- Art der Anforderung: Festanaforderung
- Quelle: ESOP
- Urheber: Tobias Oetermann

#### R107
Systemeinführung
- Aktiv: true
- Ursprung / Begründung der Anforderung: Informationen zum System
- Quelle: ESOP
- Art der Anforderung: Festanaforderung
- Bemerkung: Das System sollte dem Nutzer eine angemesse Anleitung zur Nutzung und zum Umgang mit dem System geben. Technische und juristische Systemeinschränkungen sind dabei zu berücksichtigen.
- Urheber: Tobias Oetermann
- Verantwortlichkeit: Charamel, Cerence, IKA, Saint Gobain
- Link -> R128

#### R108
Systemeinführung: Korrektheit und Einfachheit
- Aktiv: true
- Ursprung / Begründung der Anforderung: Informationen zum System
- Quelle: ESOP
- Art der Anforderung: Festanaforderung
- Bemerkung: Die Anleitung in den Umgang und die Nutzung des Systems sollte zutreffen und einfach sein.
- Urheber: Tobias Oetermann
- Verantwortlichkeit: Charamel, Cerence, IKA, Saint Gobain
- Link -> R128

#### R109
Systemeinführung: Sprache der Zielgruppe
- Aktiv: true
- Ursprung / Begründung der Anforderung: Informationen zum System
- Quelle: ESOP
- Art der Anforderung: Festanaforderung
- Bemerkung: Die Anleitung in den Umgang und die Nutzung des Systems orientiert sich in Form und Sprache an der vorgesehenen und wahrscheinlichsten Nutzerzielgruppe. Dabei sollten grundsätzlich mehrere Sprachen berücksichtigt werden.
- Urheber: Tobias Oetermann
- Verantwortlichkeit: Charamel, Cerence, IKA, Saint Gobain
- Link -> R128

#### R110
Systemeinführung: Klarheit/Verantwortlichkeit
- Aktiv: true
- Ursprung / Begründung der Anforderung: Informationen zum System
- Quelle: ESOP
- Art der Anforderung: Festanaforderung
- Bemerkung: Die Anweisung in den Umgang und die Nutzung des Systems sollte unmissverständlich Auskunft darüber geben, welche Systemfunktionen während der manuellen Fahrt genutzt werden können und bei welchen Funktionen eine Nutzung während der Fahrt nicht vorgesehen ist.
  Automatisierte Fahrzeugführung: Die Einweisung in das System vermittelt unmissverständlich, welche Verantwortlichkeit während welchem Fahrmodus bei dem System, und welche bei dem Nutzer liegen. Davon ableitend gibt die Anweisung Auskunft darüber, welche Systemfunktionen in den jeweiligen Fahrmodi genutzt werden können/dürfen, und welche für den jeweiligen Fahrmodus nicht vorgesehen und mit der Verantwortlichkeit im Widerspruch stehen.
  (Unterstützt durch DIN EN ISO 17287 - Abschnitt 4.2.5.2)
- Urheber: Tobias Oetermann
- Verantwortlichkeit: Charamel, Cerence, IKA, Saint Gobain
- Link -> R128

#### R111
Systemeinführung: Detaillierte Beschreibung
- Aktiv: true
- Ursprung / Begründung der Anforderung: Informationen zum System
- Quelle: ESOP
- Art der Anforderung: Festanaforderung
- Bemerkung: Die Anweisung in den Umgang und die Nutzung des Systems sollte unmissverständlich die Systemfunktionen beschreiben. Dabei werden sowohl die Vorteile wie auch die Systemgrenzen bzw. -einschränkungen detailliert beschrieben und so ein umfassender Überblick über das System vermittelt.
- Urheber: Tobias Oetermann
- Verantwortlichkeit: Charamel, Cerence, IKA, Saint Gobain
- Link -> R128

#### R112
Systemeinführung: Einschränkungen bezüglich der Nutzergruppe
- Aktiv: true
- Ursprung / Begründung der Anforderung: Informationen zum System
- Quelle: ESOP
- Art der Anforderung: Festanaforderung
- Bemerkung: Die Anweisung in den Umgang und die Nutzung des Systems sollte potenziell benötigte Kompetenzen der Nutzer bzw. den potenziellen Ausschluss einzelner Nutzergruppen klar formulieren.
- Urheber: Tobias Oetermann
- Verantwortlichkeit: Charamel, Cerence, IKA, Saint Gobain
- Link -> R145
- Link -> R128

#### R113
Realistische Darstellung der Funktionalität
- Aktiv: true
- Ursprung / Begründung der Anforderung: Informationen zum System
- Quelle: ESOP
- Art der Anforderung: Festanaforderung
- Bemerkung: Sämtliche mit dem System im Zusammenhang stehenden Abbildungen/Darstellungen (z.B. Skizzen, Fotos, Beschreibungen etc.) sind realistisch und wecken keine falschen Erwartungen an das System, den Systemumfang oder die Systemleistung. Der Nutzer ist somit in der Lage, sich vor und während der Nutzung ein klares Bild von den Vorteilen und Systemgrenzen zu verschaffen.
- Urheber: Tobias Oetermann
- Verantwortlichkeit: Charamel, Cerence, IKA, Saint Gobain
- Link -> R128

## R114
Situative Visualisierung
- Urheber: Tobias Oetermann
- Aktiv: true

### R115
Luft- und Raumfahrt
- Urheber: Tobias Oetermann

#### R116
Gestaltungsprinzip der Displayintegration
- Aktiv: true
- Art der Anforderung: Festanaforderung
- Quelle: Wickens (2003)
- Ursprung / Begründung der Anforderung: Benutzbarkeit
- Bemerkung: Der nutzerseitige Aufwand, eine gesuchte/notwendige Information zu finden und zu verarbeiten, hängt im wesentlichen von zwei Faktoren ab:
  1. Positionierung im Vergleich zur Normalsicht des Nutzers (vgl. Anforderung "Orientierung an Sichtlinie" der ESOP)
  2. bei zwei Informationen, die abgeglichen werden müssen (bzw. die beide Notwendig sind, um ein mentales Modell aufrecht zu erhalten - mentale Nähe der Information), ist der räumliche Abstand zwischen den Informationsorten zu minimieren (räumliche Nähe der Information).
- Urheber: Tobias Oetermann
- Verantwortlichkeit: IKA, Cerence, Charamel, Saint Gobain

#### R117
Gestaltungsprinzip des abgebildeten Realismus
- Aktiv: true
- Art der Anforderung: Festanaforderung
- Quelle: Wickens (2003)
- Ursprung / Begründung der Anforderung: Wiedererkennbarkeit
- Bemerkung: Die abgebildete Repräsentation einer Information sollte in der Art, Form, Semantik etc. den Eigenschaften der Information entsprechen (bspw. Flughöhe über eine vertikale Anzeige (hoch - runter) statt über eine runde Anzeige; Kompass in Form einer runden Anzeige etc.).
- Urheber: Tobias Oetermann
- Verantwortlichkeit: IKA, Cerence, Charamel, Saint Gobain

#### R118
Gestaltungsprinzip der Bewegung von Anzeigeteilen
- Aktiv: true
- Art der Anforderung: Festanaforderung
- Quelle: Wickens (2003)
- Ursprung / Begründung der Anforderung: Wiedererkennbarkeit
- Bemerkung: Das Gestaltungsprinzip legt nahe, dass bewegende Elemente auf einer Anzeige mit dem mentalen Modell des Nutzers zu der entsprechenden Situation übereinstimmen (bspw. Anzeige, die die Bewegung eines automatisierten Fahrzeugs durch den Verkehr innerhalb des Fahrzeugs visualisiert: Fahrzeug bleibt statisch auf dem Display, während sich der Verkehr um das Fahrzeug herum bewegt. Grundlage: Aus Sicht des Nutzers ist das Fahrzeug statisch (mentales Modell) und die restlichen Verkehrsteilnehmer bewegen sich).
- Urheber: Tobias Oetermann
- Verantwortlichkeit: Charamel, IKA, Saint Gobain

#### R119
Gestaltungsprinzip der vorausschauenden Führung
- Aktiv: true
- Art der Anforderung: Festanaforderung
- Quelle: Wickens (2003)
- Ursprung / Begründung der Anforderung: Nutzbarkeit
- Bemerkung: Die Vorausschau bzw. Prädiktion des Verhaltens hochdynamischer Systeme ist kognitiv eine große Herausforderung. Es müssen die notwendigen Informationen sondiert, erfasst und mithilfe des mentalen Modells des aktuellen Betriebsmodus analysiert werden, um eine Abschätzung der kommenden Dynamik ableiten zu können. Die Anzeige prädiktiver Informationen kann dem Nutzer stark dabei helfen, den kognitiven Aufwand zu reduzieren und die Ergebnisse der Prädiktion zu verbessern. Dies trägt aktiv zum Situationsbewusstsein bei. Wesentlich ist dabei jedoch, das die prädiktiven Informationen hoch genau sind und wenig (idealerweise keine) Fehler aufweisen.
- Urheber: Tobias Oetermann
- Verantwortlichkeit: IKA, Saint Gobain

#### R120
Gestaltungsprinzip der Unterscheidbarkeit dargestellter Informationen
- Aktiv: true
- Art der Anforderung: Festanaforderung
- Quelle: Wickens (2003)
- Ursprung / Begründung der Anforderung: Benutzbarkeit
- Bemerkung: Ein wesentliche Gestaltungsanforderung bei der Präsentation visueller Systeminformationen stellt die Unterscheidbarkeit dar: Es ist von zentraler Bedeutung, dass der Nutzer Informationen stets im richtigen Kontext wahrnimmt und es nicht zu Verwechslungen mit anderen, potenziell vorhandenen Informationen kommt (bspw. durch gleichen Wertebereich und ähnliche Repräsentation von Parametern etc.). Die Informationen müssen also eindeutig und unverwechselbar sein (vgl. Anforderung "Genauigkeit" der ESOP).
- Urheber: Tobias Oetermann
- Verantwortlichkeit: IKA, Charamel, Saint Gobain

#### R121
Darstellung auslösender Phänomene bei Dynamikwechseln
- Aktiv: true
- Art der Anforderung: Festanaforderung
- Quelle: Wickens (2003)
- Ursprung / Begründung der Anforderung: Nutzbarkeit
- Bemerkung: Die Nachvollziehbarkeit automatisierter Handlungen ist für den Nutzer ausgesprochen wichtig, um ein gefährdenden Eingreifen des Nutzers zu verhindern und zeitgleich ein positives Nutzererleben aufrecht zu erhalten. Aus diesem Grund sollten bei sich auffallend ändernden Automationszuständen (bspw. wechselnde Dynamik, plötzliche Querdynamik, stärkeres Abbremsen etc.) stets nachvollziehbar sein, warum die Automation das Manöver durchführt, welches Ziel die Automation dabei verfolgt und wie die kommende Dynamik zu erwarten ist. Dazu müssen entsprechende Anzeigen beitragen.
- Urheber: Tobias Oetermann
- Verantwortlichkeit: IKA, Saint Gobain, Charamel

## R127
Ergonomie
- Aktiv: true
- Quelle: Technologieworkshop – Expertenanforderung
- Urheber: Tobias Oetermann

### R128
Einführung in die Funktionalität des Systems
- Bemerkung: Das System sollte den Benutzer in die Funktionalitäten des Systems einführen
- Quelle: Technologieworkshop – Expertenanforderung
- Aktiv: true
- Ursprung / Begründung der Anforderung: Ergonomie
- Urheber: Tobias Oetermann
- Art der Anforderung: Festanaforderung
- Verantwortlichkeit: IKA, DFKI, Cerence, CanControls, Charamel, Saint Gobain

### R129
Einführung in Steuerung via Avatar
- Bemerkung: Avatar soll den Benutzer in die Funktionalitäten des Systems einführen, um das Vertrauen des Benutzers zu erhöhen
- Quelle: Technologieworkshop – Expertenanforderung
- Aktiv: true
- Ursprung / Begründung der Anforderung: Ergonomie
- Urheber: Tobias Oetermann
- Art der Anforderung: Festanaforderung
- Verantwortlichkeit: Cerence, Charamel, DFKI

### R130
AR Inhalte passend zur realen Darstellen (räumlich)
- Bemerkung: AR sollte immer die reale Situation adäquat darstellen. Abweichungen in Bezug auf Größen und Positionen sollten verhindert werden.
- Quelle: Technologieworkshop – Expertenanforderung
- Aktiv: true
- Ursprung / Begründung der Anforderung: Ergonomie
- Urheber: Tobias Oetermann
- Art der Anforderung: Festanaforderung
- Verantwortlichkeit: Saint Gobain, CanControls

### R131
Anzeige in Sichtlinie
- Bemerkung: Anzeigen und vor allem fahrrelevante Informationen sollten im Sichtlinie sein
- Quelle: Technologieworkshop – Expertenanforderung
- Aktiv: true
- Ursprung / Begründung der Anforderung: Ergonomie
- Urheber: Tobias Oetermann
- Art der Anforderung: Festanaforderung
- Verantwortlichkeit: IKA, Saint Gobain, Charamel

### R132
Anzeigen optisch ergonomisch gestalten
- Bemerkung: Die passende Größe, Helligkeit und Position sollten bei der Gestaltung der Displays berücksichtigt werden
- Quelle: Technologieworkshop – Expertenanforderung
- Aktiv: true
- Ursprung / Begründung der Anforderung: Ergonomie
- Urheber: Tobias Oetermann
- Art der Anforderung: Festanaforderung
- Verantwortlichkeit: Saint Gobain, IKA

### R133
Anzeigen müssen auch bei schwierigen Lichterverhältnissen lesbar sein
- Bemerkung: Eine hohe Lichtintensität aus der Umgebung ist meist kritisch für die Anzeigen. Auch in diesen Situationen sollte die Sichtbarkeit des Systems ausreichend sein.
- Quelle: Technologieworkshop – Expertenanforderung
- Aktiv: true
- Ursprung / Begründung der Anforderung: Ergonomie
- Urheber: Tobias Oetermann
- Art der Anforderung: Festanaforderung
- Verantwortlichkeit: Saint Gobain, IKA

### R134
Ausreichende Schriftgröße
- Bemerkung: Um schriftliche Informationen unter Fahrbedingungen ohne großen Aufwand lesen zu können, sollte die Schriftgröße angemessen sein.
- Quelle: Technologieworkshop – Expertenanforderung
- Aktiv: true
- Ursprung / Begründung der Anforderung: Ergonomie
- Urheber: Tobias Oetermann
- Art der Anforderung: Festanaforderung
- Verantwortlichkeit: Saint Gobain, IKA, Charamel

### R135
System sollte intuitiv bedienbar sein
- Bemerkung: Das System sollte intuitiv bedienbar sein: logische Anordnung, Verwendung von Symbolen, einfache Erlernbarkeit
- Quelle: Technologieworkshop – Expertenanforderung
- Aktiv: true
- Ursprung / Begründung der Anforderung: Ergonomie
- Urheber: Tobias Oetermann
- Art der Anforderung: Festanaforderung
- Verantwortlichkeit: IKA, Cerence, CanControls, Charamel, Saint Gobain

### R136
Gestik
- Quelle: Technologieworkshop – Expertenanforderung
- Aktiv: true
- Ursprung / Begründung der Anforderung: Ergonomie
- Urheber: Tobias Oetermann

#### R137
System soll Handgesten erkennen
- Bemerkung: System sollte Handgesten des Benutzers erkennen. Diese Gesten sollen bei der Kommunikation mit dem System oder zur Bewertung des Nutzerzustands verwendet werden.
- Quelle: Technologieworkshop – Expertenanforderung
- Aktiv: true
- Ursprung / Begründung der Anforderung: Ergonomie
- Urheber: Tobias Oetermann
- Art der Anforderung: Wunschanforderung
- Verantwortlichkeit: CanControls

#### R138
System soll Kopfgesten erkennen
- Bemerkung: System sollte Kopfgesten des Benutzers zu erkennen. Diese Gesten sollen bei der Kommunikation mit dem System oder bei der Bewertung des Nutzerzustands verwendet werden.
- Quelle: Technologieworkshop – Expertenanforderung
- Aktiv: true
- Ursprung / Begründung der Anforderung: Ergonomie
- Urheber: Tobias Oetermann
- Art der Anforderung: Wunschanforderung
- Verantwortlichkeit: CanControls

#### R139
Individuelle Gestiken, an den jeweiligen Nutzer angepasst
- Bemerkung: System sollte so konzipiert sein, dass es die Gesten erkennt, auch wenn sie von Benutzer zu Benutzer in Nuancen variieren (Lernfähigkeit)
- Quelle: Technologieworkshop – Expertenanforderung
- Aktiv: true
- Ursprung / Begründung der Anforderung: Ergonomie
- Urheber: Tobias Oetermann
- Art der Anforderung: Wunschanforderung
- Verantwortlichkeit: CanControls

### R140
System sollte verständliches Rückmeldungen geben
- Bemerkung: Rückmeldung als Reaktion auf eine Nutzereingabe (oder Veränderung des automatisierten Fahrzustandes) sollte klar, verständlich und rechtzeitig erfolgen
- Quelle: Technologieworkshop – Expertenanforderung
- Aktiv: true
- Ursprung / Begründung der Anforderung: Ergonomie
- Urheber: Tobias Oetermann
- Art der Anforderung: Festanaforderung
- Verantwortlichkeit: IKA, Charamel, Saint Gobain, Cerence

### R141
Das System sollte die aktuelle Fahrsituation/Automationszustand und das weitere geplanten Vorgehen erklären (Vorhersehbarkeit/Antizipierbarkeit)
- Bemerkung: System sollte Informationen über Geschwindigkeit, Navigation, Systemstatus, aber auch über zukünftige Trajektorien, Bremspunkte und andere Fahrzeuge (V2V-Kommunikation) geben.
- Quelle: Technologieworkshop – Expertenanforderung
- Aktiv: true
- Ursprung / Begründung der Anforderung: Ergonomie
- Urheber: Tobias Oetermann
- Art der Anforderung: Festanaforderung
- Verantwortlichkeit: Saint Gobain, IKA

### R142
Redundanz
- Bemerkung: Bei Bedarf (insbesondere in kritischen Situationen) sollten redundante Informationen zur Verfügung stehen. Zum Beispiel akustische und visuelle Signale (Multimodalität)
- Quelle: Technologieworkshop – Expertenanforderung
- Aktiv: true
- Ursprung / Begründung der Anforderung: Ergonomie
- Urheber: Tobias Oetermann
- Art der Anforderung: Festanaforderung
- Verantwortlichkeit: IKA, Cerence, Charamel, Saint Gobain

### R143
Erfassung des Nutzerverhaltens und des Nutzerzustands
- Bemerkung: Durch die Erfassung der akustischen und visuellen Daten sollte das System in der Lage sein, den Zustand des Benutzers zu bestimmen
- Quelle: Technologieworkshop – Expertenanforderung
- Aktiv: true
- Ursprung / Begründung der Anforderung: Ergonomie
- Urheber: Tobias Oetermann
- Art der Anforderung: Festanaforderung
- Verantwortlichkeit: Cerence, CanControls, DFKI

### R144
Anpassung an das Nutzerverhalten und den Nutzerzustand, um das Nutzervertrauen zu erhöhen
- Bemerkung: Nach der Detektion von Schwankungen des Nutzervertrauenszustandes sollte das System reagieren, um das Vertrauen des Nutzers zu kalibrieren/festigen
- Quelle: Technologieworkshop – Expertenanforderung
- Aktiv: true
- Ursprung / Begründung der Anforderung: Ergonomie
- Urheber: Tobias Oetermann
- Art der Anforderung: Festanaforderung
- Verantwortlichkeit: IKA, DFKI, Cerence, CanControls, Charamel, Saint Gobain

### R145
Interaktionen f. Menschen mit einschränkungen ermöglichen
- Bemerkung: Multimodale Interaktionen können Menschen mit körperlichen Einschränkungen die effektive Nutzung des Systems ermöglichen
- Quelle: Technologieworkshop – Expertenanforderung
- Aktiv: true
- Ursprung / Begründung der Anforderung: Ergonomie
- Urheber: Tobias Oetermann
- Art der Anforderung: Wunschanforderung
- Verantwortlichkeit: IKA, DFKI, Cerence, CanControls, Charamel, Saint Gobain

### R146
Ergonomische Sitzposition
- Bemerkung: Die Sitzpositionen sollten bequem sein und alle Bedienelemente sollten erreichbar sein (konventionelle Sitzposition)
- Quelle: Technologieworkshop – Expertenanforderung
- Aktiv: true
- Ursprung / Begründung der Anforderung: Ergonomie
- Urheber: Tobias Oetermann
- Art der Anforderung: Festanaforderung
- Verantwortlichkeit: IKA, Cerence, CanControls, Charamel, Saint Gobain

### R147
Ergonomische Adaptierbarkeit (verschiedene Nutzer)
- Bemerkung: Anpassungen an die persönlichen Wünsche und körperlichen Bedürfnisse aller Nutzer ermöglichen
- Quelle: Technologieworkshop – Expertenanforderung
- Aktiv: true
- Urheber: Tobias Oetermann
- Art der Anforderung: Festanaforderung
- Verantwortlichkeit: IKA, Cerence, CanControls, Charamel, Saint Gobain

### R148
Adaptivität des Avatarverhaltens
- Bemerkung: Avatar soll das Verhalten abhängig vom Benutzerzustand anpassen
- Quelle: Technologieworkshop – Expertenanforderung
- Aktiv: true
- Ursprung / Begründung der Anforderung: Ergonomie
- Urheber: Tobias Oetermann
- Art der Anforderung: Festanaforderung
- Verantwortlichkeit: Charamel, DFKI

### R149
Kompatibilität mit anderen Fahrzeugsystemen
- Bemerkung: Kompatibilität mit anderen Fahrzeugsystemen, insbesondere den Systemen für die primäre Fahraufgabe
- Quelle: Technologieworkshop – Expertenanforderung
- Aktiv: true
- Ursprung / Begründung der Anforderung: Ergonomie
- Urheber: Tobias Oetermann
- Art der Anforderung: Festanaforderung
- Verantwortlichkeit: IKA, Cerence, CanControls, Charamel, Saint Gobain

## R150
Markt
- Quelle: Technologieworkshop – Expertenanforderung
- Aktiv: true
- Urheber: Tobias Oetermann

### R151
Das System sollte für alle Altersgruppen geeignet sein, unabhängig vom Grad der Fahrerfahrung
- Bemerkung: Das System sollte für alle Nutzer hilfreich sein (Fahranfänger bis Berufsfahrer)
- Quelle: Technologieworkshop – Expertenanforderung
- Aktiv: true
- Ursprung / Begründung der Anforderung: Markt
- Urheber: Tobias Oetermann
- Art der Anforderung: Festanaforderung
- Verantwortlichkeit: IKA, DFKI, Cerence, CanControls, Charamel, Saint Gobain

### R152
Abo-Dienste ermöglichen (Karte, Cloud-Service, Updates)
- Bemerkung: Unterschiedliche Abo-Dienste umsetzen (Karte, Cloud-Service, Updates) - Geschäftsmodell
- Quelle: Technologieworkshop – Expertenanforderung
- Aktiv: true
- Ursprung / Begründung der Anforderung: Markt
- Urheber: Tobias Oetermann
- Art der Anforderung: Wunschanforderung
- Verantwortlichkeit: IKA, DFKI, Cerence, CanControls, Charamel, Saint Gobain

### R153
Systempreis sollte den Einbau in Fahrzeuge der oberen Mittelklasse ermöglichen
- Bemerkung: Der Preis des Systems sollte in einem Rahmen gehalten sein, der den Preis des Fahrzeugs der oberen Mittelklasse nicht signifikant erhöht
- Quelle: Technologieworkshop – Expertenanforderung
- Aktiv: true
- Ursprung / Begründung der Anforderung: Markt
- Urheber: Tobias Oetermann
- Art der Anforderung: Wunschanforderung
- Verantwortlichkeit: IKA, Cerence, CanControls, Charamel, Saint Gobain

### R154
Übertragbarkeit auf andere Märkte (USA, China etc.)
- Bemerkung: System sollte einfach in Übereinstimmung mit regionalen Gesetzen und Normen modifiziert werden können (AAM, JAMA, etc.). Lokale Benutzerbedürfnisse sollten berücksichtigt werden. Avatar sollte regionsspezifisches Aussehen haben.
- Quelle: Technologieworkshop – Expertenanforderung
- Aktiv: true
- Ursprung / Begründung der Anforderung: Markt
- Urheber: Tobias Oetermann
- Art der Anforderung: Wunschanforderung
- Verantwortlichkeit: IKA, DFKI, Cerence, CanControls, Charamel, Saint Gobain
- Link -> R232
- Link -> R231

### R155
Anpassungsfähigkeit an automatisierten Taxidienst
- Bemerkung: Das System ist so zu gestalten, dass es an einfach für ein automatisiertes Taxi/Shuttle angepasst werden kann
- Quelle: Technologieworkshop – Expertenanforderung
- Aktiv: true
- Ursprung / Begründung der Anforderung: Markt
- Urheber: Tobias Oetermann
- Art der Anforderung: Wunschanforderung
- Verantwortlichkeit: IKA, DFKI, Cerence, CanControls, Charamel, Saint Gobain

### R156
Ermöglichen Avatar-Customization als B2C Element
- Bemerkung: Ermöglicht die Avataranpassung von Vorbestellungen nach Kundenwunsch
- Quelle: Technologieworkshop – Expertenanforderung
- Aktiv: true
- Ursprung / Begründung der Anforderung: Markt
- Urheber: Tobias Oetermann
- Art der Anforderung: Wunschanforderung
- Verantwortlichkeit: Charamel
- Link -> R232
- Link -> R231

### R157
Anpassungen ermöglichen durch Community Content / DLCs
- Bemerkung: Möglichkeit, die Systemschnittstelle durch Community-Content oder DLCs (Downloadable Content) zu modifizieren oder zu erweitern (Aftermarket)
- Quelle: Technologieworkshop – Expertenanforderung
- Aktiv: true
- Ursprung / Begründung der Anforderung: Markt
- Urheber: Tobias Oetermann
- Art der Anforderung: Wunschanforderung
- Verantwortlichkeit: IKA, DFKI, Cerence, CanControls, Charamel, Saint Gobain

### R158
Grundlegende Vertrauensbasis schon während Vermarktung (vor Erwerb) schaffen (Markenbild)
- Bemerkung: Marketingaktivitäten und Systempräsentationen sollen das Vertrauen des Nutzers schon vor Beginn der Nutzung des Systems erhöhen.
- Quelle: Technologieworkshop – Expertenanforderung
- Aktiv: true
- Ursprung / Begründung der Anforderung: Markt
- Urheber: Tobias Oetermann
- Art der Anforderung: Wunschanforderung
- Verantwortlichkeit: IKA, DFKI, Cerence, CanControls, Charamel, Saint Gobain

### R159
Grundsystem adaptierbar an verschiedene Preisklassen (Baukasten)
- Bemerkung: Das Basissystem sollte modular sein, um das Entfernen von Funktionen und Subsystemen zu ermöglichen, um an unterschiedliche Preisklassen anpassbar zu sein (mehr Funktionen in der höheren Klasse, weniger Funktionen in der niedrigeren Klasse)
- Quelle: Technologieworkshop – Expertenanforderung
- Aktiv: true
- Ursprung / Begründung der Anforderung: Markt
- Urheber: Tobias Oetermann
- Art der Anforderung: Wunschanforderung
- Verantwortlichkeit: IKA, DFKI, Cerence, CanControls, Charamel, Saint Gobain

## R160
Geometrie
- Quelle: Technologieworkshop – Expertenanforderung
- Aktiv: true
- Urheber: Tobias Oetermann

### R161
Vollflächige Nutzung der Windschutz-scheibe
- Bemerkung: HUD sollte die gesamte Fläche der Windschutzscheibe nutzen
- Quelle: Technologieworkshop – Expertenanforderung
- Aktiv: true
- Ursprung / Begründung der Anforderung: Geometrie
- Urheber: Tobias Oetermann
- Art der Anforderung: Festanaforderung
- Verantwortlichkeit: Saint Gobain

### R163
Touchbedienung unter Berücksichtigung schwingender Fahrzeuganregung
- Bemerkung: Bedienelemente und Anzeigen sollten unter Berücksichtigung der normalen Fahrzeugbewegungen und damit zusammenhängenden Schwingungen des Armes bzw. der Hand dimensioniert und positioniert werden
- Quelle: Technologieworkshop – Expertenanforderung
- Aktiv: true
- Ursprung / Begründung der Anforderung: Geometrie
- Urheber: Tobias Oetermann
- Art der Anforderung: Festanaforderung
- Verantwortlichkeit: IKA

### R164
Innenraumkameras nicht sichtbar platzieren
- Bemerkung: Kameras sollten nicht sichtbar sein oder zumindest den Innenraum nicht nachteilig verändern
- Quelle: Technologieworkshop – Expertenanforderung
- Aktiv: true
- Ursprung / Begründung der Anforderung: Geometrie
- Urheber: Tobias Oetermann
- Art der Anforderung: Wunschanforderung
- Verantwortlichkeit: CanControls

### R165
Innenraummikrofone nicht sichtbar platziert
- Bemerkung: Mikrofone sollten nicht sichtbar sein oder zumindest den Innenraum nicht nachteilig verändern
- Quelle: Technologieworkshop – Expertenanforderung
- Aktiv: true
- Ursprung / Begründung der Anforderung: Geometrie
- Urheber: Tobias Oetermann
- Art der Anforderung: Wunschanforderung
- Verantwortlichkeit: Cerence

### R166
Innenraumkameras mit zusätzlichen Funktionalitäten
- Bemerkung: Dieselben Kameras sollten für die Bewertung des Nutzervertrauenszustandes (Nutzerbeobachtung) und für Videoanrufe verwendet werden
- Quelle: Technologieworkshop – Expertenanforderung
- Aktiv: true
- Ursprung / Begründung der Anforderung: Geometrie
- Urheber: Tobias Oetermann
- Art der Anforderung: Wunschanforderung
- Verantwortlichkeit: CanControls

### R257
Innenraummikrofone mit zusätzlichen Funktionalitäten
- Aktiv: true
- Art der Anforderung: Wunschanforderung
- Quelle: Technologieworkshop – Expertenanforderung
- Ursprung / Begründung der Anforderung: Geometrie
- Urheber: Tobias Oetermann
- Verantwortlichkeit: Cerence
- Bemerkung: Dieselben Mikrofone sollten für die Bewertung des Nutzervertrauenszustandes (Nutzerbeobachtung) und für Videoanrufe (Audio) verwendet werden

### R167
Minimaler Bauraum (für Kameras und Mikrofone)
- Bemerkung: Die Mikrofone und Kameras sollten möglichst geringe Abmessungen haben, um eine einfache Integration zu ermöglichen und das Aussehen des Innenraums möglichst nicht zu beeinflussen
- Quelle: Technologieworkshop – Expertenanforderung
- Aktiv: true
- Ursprung / Begründung der Anforderung: Geometrie
- Urheber: Tobias Oetermann
- Art der Anforderung: Wunschanforderung
- Verantwortlichkeit: Cerence, CanControls

### R168
Sensorik/Hardware darf sich nicht gegenseitig nachteilig beeinflussen
- Bemerkung: Sensorik und Hardware dürfen sich nicht gegenseitig nachteilig beeinflussen, um eine stabile Arbeit des Systems zu gewährleisten
- Quelle: Technologieworkshop – Expertenanforderung
- Aktiv: true
- Ursprung / Begründung der Anforderung: Geometrie
- Urheber: Tobias Oetermann
- Art der Anforderung: Festanaforderung
- Verantwortlichkeit: IKA, Cerence, CanControls, Charamel, Saint Gobain

### R169
Assistent/Avatar sichtbar für alle Insassen
- Bemerkung: Der Avatar (intelligenter Assistent) sollte von jedem Innenraumplatz her sichtbar sein, um allen Insassen eine Interaktion zu ermöglichen (mit visuellem Feedback)
- Quelle: Technologieworkshop – Expertenanforderung
- Aktiv: true
- Ursprung / Begründung der Anforderung: Geometrie
- Urheber: Tobias Oetermann
- Art der Anforderung: Wunschanforderung
- Verantwortlichkeit: Charamel, Saint Gobain, IKA

### R170
Gemeinsamen Inhalt (Anzeige) für alle Fahrgäste mittig positionieren
- Bemerkung: Blickstrategie des Nutzers berücksichtigen. "Weite Wege" fürs Auge ggf. anstrengend. Deshalb für alle Insassen relevante Informationen (oder Entertainment) zentral positionieren
- Quelle: Technologieworkshop – Expertenanforderung
- Aktiv: true
- Ursprung / Begründung der Anforderung: Geometrie
- Urheber: Tobias Oetermann
- Art der Anforderung: Festanaforderung
- Verantwortlichkeit: IKA

### R171
Anordnung der Informationen (Anzeigeorte), Sitzposition und Einstellungen konfigurierbar (mit Nutzungsprofilen)
- Bemerkung: Durch Sprach- und/oder Gesichtserkennung werden automatisch Nutzerprofile geladen, welche die Sitzposition, die Anzeigen und Einstellungen an die Wünsche und Bedürfnisse des Nutzers anpasst
- Quelle: Technologieworkshop – Expertenanforderung
- Aktiv: true
- Ursprung / Begründung der Anforderung: Geometrie
- Urheber: Tobias Oetermann
- Art der Anforderung: Wunschanforderung
- Verantwortlichkeit: IKA, Cerence, CanControls, Charamel, Saint Gobain

### R172
Bewegliche/Verschiebbare Teile dürfen sich nicht von selbst während der Fahrt verschieben
- Bemerkung: Um die Sicherheit zu gewährleisten, müssen Teile fixiert werden
- Quelle: Technologieworkshop – Expertenanforderung
- Aktiv: true
- Ursprung / Begründung der Anforderung: Geometrie
- Urheber: Tobias Oetermann
- Art der Anforderung: Festanaforderung
- Verantwortlichkeit: IKA, Cerence, CanControls, Charamel, Saint Gobain

## R162
Features
- Quelle: Technologieworkshop – Expertenanforderung
- Aktiv: true
- Urheber: Tobias Oetermann

### R174
Möglichkeit, verschiedene Arten von Apps und Unterhaltung zu nutzen
- Bemerkung: Möglichkeit, verschiedene Arten von Apps und Unterhaltung zu nutzen während der automatisierten Fahrt (Netflix, Live TV, Video-Streaming, Mail)
- Quelle: Technologieworkshop – Expertenanforderung
- Aktiv: true
- Ursprung / Begründung der Anforderung: Features
- Urheber: Tobias Oetermann
- Art der Anforderung: Wunschanforderung
- Verantwortlichkeit: IKA

### R175
Darstellung der Fahrtrajektorie in der Windschutzscheibe
- Bemerkung: Die Fahrtrajektorie soll in der Windschutzscheibe dargestellt werden. Das ermöglicht dem Benutzer, die geplante Bahnführung in der realen Umgebung zu erkennen
- Quelle: Technologieworkshop – Expertenanforderung
- Aktiv: true
- Ursprung / Begründung der Anforderung: Features
- Urheber: Tobias Oetermann
- Art der Anforderung: Festanaforderung
- Verantwortlichkeit: Saint Gobain, CanControls

### R176
Konnektivität und Interoperabilität mit anderen persönlichen Geräten
- Bemerkung: iOS, Andriod, Apps, etc.
  Nutzung von Smartphone Funktionen im Fahrzeug (bspw. WhatsApp in Windschutzscheibe oder Instrumentcluster)
- Quelle: Technologieworkshop – Expertenanforderung
- Aktiv: true
- Ursprung / Begründung der Anforderung: Features
- Urheber: Tobias Oetermann
- Art der Anforderung: Wunschanforderung
- Verantwortlichkeit: IKA
- Link -> R192

### R177
Synchronisation mit anderen persönlichen Geräten
- Bemerkung: System sollte die Synchronisation mit anderen Geräten und Apps durchführen (Kalender, E-Mail, Adressen...)
- Quelle: Technologieworkshop – Expertenanforderung
- Aktiv: true
- Ursprung / Begründung der Anforderung: Features
- Urheber: Tobias Oetermann
- Art der Anforderung: Wunschanforderung
- Verantwortlichkeit: IKA
- Link -> R192

### R178
Fahrprofilspezifische Umweltparameter nach Nutzerwunschvisualisieren
- Bemerkung: Kraftstoffverbrauch, Stromverbrauch, CO2
- Quelle: Technologieworkshop – Expertenanforderung
- Aktiv: true
- Ursprung / Begründung der Anforderung: Features
- Urheber: Tobias Oetermann
- Art der Anforderung: Wunschanforderung
- Verantwortlichkeit: Saint Gobain, IKA

### R179
Videoanruf/Videokonferenz
- Bemerkung: Videoanruf/Videokonferenz im Fahrzeug (während automatisierter Fahrt) ermöglichen. Alle Teilnehmer (Konferenztool) in Windschutzscheibe darstellen.
- Quelle: Technologieworkshop – Expertenanforderung
- Aktiv: true
- Ursprung / Begründung der Anforderung: Features
- Urheber: Tobias Oetermann
- Art der Anforderung: Wunschanforderung
- Verantwortlichkeit: Saint Gobain, CanControls, Cerence, IKA

### R180
Office Modus
- Bemerkung: Das System sollte einen Office Modus ermöglichen und dafür ein geeignetes Eingabegerät bereitstellen (Tastatur - entweder physisch oder als Display)
- Quelle: Technologieworkshop – Expertenanforderung
- Aktiv: true
- Ursprung / Begründung der Anforderung: Features
- Urheber: Tobias Oetermann
- Art der Anforderung: Wunschanforderung
- Verantwortlichkeit: IKA

## R173
Schnittstellen
- Quelle: Technologieworkshop – Expertenanforderung
- Aktiv: true
- Urheber: Tobias Oetermann

### R182
12 V elektrischer Anschluss
- Bemerkung: Das System sollte mit dem Standard-12-V-Fahrzeugbordnetz kompatibel sein
- Quelle: Technologieworkshop – Expertenanforderung
- Aktiv: true
- Ursprung / Begründung der Anforderung: Schnittstellen
- Urheber: Tobias Oetermann
- Art der Anforderung: Festanaforderung
- Verantwortlichkeit: IKA, Cerence, CanControls, Charamel, Saint Gobain

### R183
Geringer Verbrauch
- Bemerkung: System soll möglichst wenig Energie verbrauchen
- Quelle: Technologieworkshop – Expertenanforderung
- Aktiv: true
- Ursprung / Begründung der Anforderung: Schnittstellen
- Urheber: Tobias Oetermann
- Art der Anforderung: Festanaforderung
- Verantwortlichkeit: IKA, Cerence, CanControls, Charamel, Saint Gobain

### R184
Flüssige Datenübertragung
- Bemerkung: Flüssige Daten-/Informationsübertragung zwischen den Teilsystemen: Keine Verzögerungen zwischen Interaktion und Systemreaktion
- Quelle: Technologieworkshop – Expertenanforderung
- Aktiv: true
- Ursprung / Begründung der Anforderung: Schnittstellen
- Urheber: Tobias Oetermann
- Art der Anforderung: Festanaforderung
- Verantwortlichkeit: IKA, DFKI, Cerence, CanControls, Charamel, Saint Gobain

### R185
Rechenleistung ausreichend, um flüssige Interaktion zu ermöglichen
- Bemerkung: Die Eingabe des Nutzers erzeugt eine zeitnahe und angemessen systemische Reaktion (Rückmeldung, Bestätigung etc.)
- Quelle: Technologieworkshop – Expertenanforderung
- Aktiv: true
- Ursprung / Begründung der Anforderung: Schnittstellen
- Urheber: Tobias Oetermann
- Art der Anforderung: Festanaforderung
- Verantwortlichkeit: IKA, DFKI, Cerence, CanControls, Charamel, Saint Gobain
- Link -> R247

### R186
Schnittstellen des Fahrzeugs berücksichtigen (CAN etc.)
- Bemerkung: Vorhandene Schnittstellen (CAN) sollten, wenn möglich, genutzt werden, um die Komplexität und den Preis des Systems zu reduzieren
- Quelle: Technologieworkshop – Expertenanforderung
- Aktiv: true
- Ursprung / Begründung der Anforderung: Schnittstellen
- Urheber: Tobias Oetermann
- Art der Anforderung: Wunschanforderung
- Verantwortlichkeit: IKA, Cerence, CanControls, Charamel, Saint Gobain

### R187
Geringe Abmaße der Verbindungen (kleine Steckverbinder)
- Bemerkung: Minimierung des benötigten Bauraums
- Quelle: Technologieworkshop – Expertenanforderung
- Aktiv: true
- Ursprung / Begründung der Anforderung: Schnittstellen
- Urheber: Tobias Oetermann
- Art der Anforderung: Wunschanforderung
- Verantwortlichkeit: IKA, Cerence, CanControls, Charamel, Saint Gobain

### R188
Verhindern thermischer Einflüsse
- Bemerkung: Systemkomponenten sollten die Temperatur anderer Fahrzeugkomponenten oder des Fahrzeuginnenraums nicht erhöhen. Die Fahrgäste sollten nicht dem warmen Luftstrom der Kühlung der Systemkomponenten ausgesetzt sein.
- Quelle: Technologieworkshop – Expertenanforderung
- Aktiv: true
- Ursprung / Begründung der Anforderung: Schnittstellen
- Urheber: Tobias Oetermann
- Art der Anforderung: Festanaforderung
- Verantwortlichkeit: IKA, Cerence, CanControls, Charamel, Saint Gobain

### R189
Kabel sollten abgedeckt werden
- Bemerkung: Um die Sicherheit zu gewährleisten, dürfen keine offenen Kabel sichtbar sein
- Quelle: Technologieworkshop – Expertenanforderung
- Aktiv: true
- Ursprung / Begründung der Anforderung: Schnittstellen
- Urheber: Tobias Oetermann
- Art der Anforderung: Festanaforderung
- Verantwortlichkeit: IKA, Cerence, CanControls, Charamel, Saint Gobain

### R190
Einheitliche Schnittstellen der Systemkomponenten
- Bemerkung: Um die Komplexität der Verkabelung zu reduzieren, sollten (wenn möglich) einheitliche Schnittstellen der Systemkomponenten genutzt werden
- Quelle: Technologieworkshop – Expertenanforderung
- Aktiv: true
- Ursprung / Begründung der Anforderung: Schnittstellen
- Urheber: Tobias Oetermann
- Art der Anforderung: Wunschanforderung
- Verantwortlichkeit: IKA, DFKI, Cerence, CanControls, Charamel, Saint Gobain

### R191
Hohe Bandbreite des Netzwerks (Traffic)
- Bemerkung: Hohe Bandbreite des Netzwerks(Traffic) (Streaming aller Features, eventuell Bilder, Video etc.)
- Quelle: Technologieworkshop – Expertenanforderung
- Aktiv: true
- Ursprung / Begründung der Anforderung: Schnittstellen
- Urheber: Tobias Oetermann
- Art der Anforderung: Wunschanforderung
- Verantwortlichkeit: IKA, DFKI, Cerence, CanControls, Charamel, Saint Gobain

### R192
Bluetooth Konnektivität
- Bemerkung: System sollte Bluetooth-Verbindung haben, um eine Kopplung beispielsweise des Smartphones zu ermöglichen
- Quelle: Technologieworkshop – Expertenanforderung
- Aktiv: true
- Ursprung / Begründung der Anforderung: Schnittstellen
- Urheber: Tobias Oetermann
- Art der Anforderung: Wunschanforderung
- Verantwortlichkeit: IKA, Cerence, CanControls, Charamel, Saint Gobain

### R193
Externe Kommunikation über 5G
- Bemerkung: Das System sollte die Möglichkeit haben, das schnelle 5G-Netzwerk für die Kommunikation zu nutzen
- Quelle: Technologieworkshop – Expertenanforderung
- Aktiv: true
- Ursprung / Begründung der Anforderung: Schnittstellen
- Urheber: Tobias Oetermann
- Art der Anforderung: Wunschanforderung
- Verantwortlichkeit: IKA, Cerence, CanControls, Charamel, Saint Gobain

### R194
Interne Bereitsstellung von Wlan
- Bemerkung: System sollte WLAN für die interne Verbindung bereitstellen.
- Quelle: Technologieworkshop – Expertenanforderung
- Aktiv: true
- Ursprung / Begründung der Anforderung: Schnittstellen
- Urheber: Tobias Oetermann
- Art der Anforderung: Wunschanforderung
- Verantwortlichkeit: IKA, Cerence, CanControls, Charamel, Saint Gobain

### R195
Energieversorgungim Fahrzeug für externe Geräte ermögliche (Smartphones etc.)
- Bemerkung: Das System sollte über ausreichende Anschlüsse verfügen, um das Laden der üblichen mobilen Geräte zu ermöglichen
- Quelle: Technologieworkshop – Expertenanforderung
- Aktiv: true
- Ursprung / Begründung der Anforderung: Schnittstellen
- Urheber: Tobias Oetermann
- Art der Anforderung: Wunschanforderung
- Verantwortlichkeit: IKA, Cerence, CanControls, Charamel, Saint Gobain

### R196
Keine Vibrationen auf Displays und Eingaben
- Bemerkung: Ermöglichen einer sicheren Montage der Geräte und verhindern von starken Vibrationen während der Fahrt
- Quelle: Technologieworkshop – Expertenanforderung
- Aktiv: true
- Ursprung / Begründung der Anforderung: Schnittstellen
- Urheber: Tobias Oetermann
- Art der Anforderung: Festanaforderung
- Verantwortlichkeit: IKA

### R197
C2X Kommunikation
- Bemerkung: C2X-Kommunikation (Car to X) soll ermöglicht werden, insbesondere für Kommunikation zwischen verschiedenen Fahrzeugensowie zwischen dem Fahrzeug und der Verkehrssteuerungsinfrastruktur.
- Quelle: Technologieworkshop – Expertenanforderung
- Aktiv: true
- Ursprung / Begründung der Anforderung: Schnittstellen
- Urheber: Tobias Oetermann
- Art der Anforderung: Wunschanforderung
- Verantwortlichkeit: IKA, Cerence, CanControls, Charamel, Saint Gobain

## R181
Sicherheit
- Quelle: Technologieworkshop – Expertenanforderung
- Aktiv: true
- Urheber: Tobias Oetermann

### R199
Indirekte Fahrzeugführung nur innerhalb der sicherheitsrelevanten Barrieren
- Bemerkung: Die automatisierte Fahrt muss innerhalb der sicherheitsrelevanten Grenzen gehalten werden. Die indirekte Fahrzeugführung sollte in Übereinstimmung mit diesen auferlegten Grenzen Einfluss auf die automatisierte Fahrt (Parametrisierung) ausüben können.
- Quelle: Technologieworkshop – Expertenanforderung
- Aktiv: true
- Ursprung / Begründung der Anforderung: Sicherheit
- Urheber: Tobias Oetermann
- Art der Anforderung: Festanaforderung
- Verantwortlichkeit: IKA

### R200
Kein Überstimmen der Automation
- Bemerkung: Eine Überstimmung der Automation (manueller Eingriff in die Fahrzeugführung) sollte unter Berücksichtigung der gesetzlichen Vorgaben stets vermieden werden (Gefährdungspotenzial).
- Quelle: Technologieworkshop – Expertenanforderung
- Aktiv: true
- Ursprung / Begründung der Anforderung: Sicherheit
- Urheber: Tobias Oetermann
- Art der Anforderung: Begeisterungsanforderung
- Verantwortlichkeit: IKA

### R259
Überlappungdurch Anzeigen in kritischen Sichtbereichenverhindern
- Aktiv: true
- Art der Anforderung: Festanaforderung
- Quelle: Technologieworkshop – Expertenanforderung
- Ursprung / Begründung der Anforderung: Sicherheit
- Bemerkung: System/Anzeige sollte gestaltet sein, dass es in kritischen Sichtbereichen nicht zu Überlappungen kommt.
- Verantwortlichkeit: IKA, Saint Gobain, Charamel
- Urheber: Tobias Oetermann

### R201
Redundante Anzeige, falls sicherheitsrelevante Systeme ausfallen
- Bemerkung: Das System sollte über redundante Anzeigen verfügen, um zu verhindern, dass bei einem Ausfall bestimmter Anzeigen die Informationen vollständig verloren werden.
- Quelle: Technologieworkshop – Expertenanforderung
- Aktiv: true
- Ursprung / Begründung der Anforderung: Sicherheit
- Urheber: Tobias Oetermann
- Art der Anforderung: Wunschanforderung
- Verantwortlichkeit: IKA, Saint Gobain, Charamel, Cerence

### R202
Moduswechsel (Automation – Manuell; Manuell – Automation) ankündigen
- Bemerkung: System muss den Moduswechsel immer und frühzeitig ankündigen.
- Quelle: Technologieworkshop – Expertenanforderung
- Aktiv: true
- Ursprung / Begründung der Anforderung: Sicherheit
- Urheber: Tobias Oetermann
- Art der Anforderung: Festanaforderung
- Verantwortlichkeit: IKA, Charamel, Cerence, Saint Gobain

### R203
Nachfragen bei kritischen Anforderungen/Kommandos
- Bemerkung: Der Nutzer muss sicherheitsrelevante Anforderungen und Kommandos immer bestätigen.
- Quelle: Technologieworkshop – Expertenanforderung
- Aktiv: true
- Ursprung / Begründung der Anforderung: Sicherheit
- Urheber: Tobias Oetermann
- Art der Anforderung: Festanaforderung
- Verantwortlichkeit: IKA, Charamel, Saint Gobain, Cerence

### R204
Systemintegrität durch Redundanz
- Bemerkung: In Hinblick auf die Zulassungsfähigkeit im automotiven Kontext sowie die Wahrung der Verkehrssicherheit (Serienproduktion) sollten die relevanten Systemelemente redundant ausgelegt werden (Hardware, ECU, Signal etc.)
- Quelle: Technologieworkshop – Expertenanforderung
- Aktiv: true
- Ursprung / Begründung der Anforderung: Sicherheit
- Urheber: Tobias Oetermann
- Art der Anforderung: Wunschanforderung
- Verantwortlichkeit: IKA, Cerence, CanControls, Charamel, Saint Gobain

### R205
System muss „Fail Safe” sein
- Bemerkung: Das System muss im Falle eines Ausfalls oder einer Fehlfunktion in einen sicheren Zustand wechseln
- Quelle: Technologieworkshop – Expertenanforderung
- Aktiv: true
- Ursprung / Begründung der Anforderung: Sicherheit
- Urheber: Tobias Oetermann
- Art der Anforderung: Festanaforderung
- Verantwortlichkeit: IKA, Cerence, CanControls, Charamel, Saint Gobain

### R206
Datensicherheit
- Bemerkung: Übereinstimmung mit DSGVO
- Quelle: Technologieworkshop – Expertenanforderung
- Aktiv: true
- Ursprung / Begründung der Anforderung: Sicherheit
- Urheber: Tobias Oetermann
- Art der Anforderung: Festanaforderung
- Verantwortlichkeit: IKA, DFKI, Cerence, CanControls, Charamel, Saint Gobain

### R207
IT Sicherheit sicherstellen (Cybersecurity)
- Bemerkung: Übereinstimmung mit ECE-R155
- Quelle: Technologieworkshop – Expertenanforderung
- Aktiv: true
- Ursprung / Begründung der Anforderung: Sicherheit
- Urheber: Tobias Oetermann
- Art der Anforderung: Festanaforderung
- Verantwortlichkeit: IKA, DFKI, Cerence, CanControls, Charamel, Saint Gobain

### R208
ASIL B bei Primäraufgabe (indirekte Fahrzeugführung) sicherstellen
- Bemerkung: Für das Integritätsniveau in Bezug auf die Fahrzeugsicherheit existiert ein Risikoklassifizierungsschema, das in der Norm ISO 26262 - Funktionale Sicherheit für Straßenfahrzeuge definiert wird. Für die indirekte Fahrzeugführung, als System, welches einen Einfluss auf die primäre Fahraufgabe hat, sollte ASIL B eingehalten werden können, um einen Serieneinsatz der Technologie ermöglichen zu können.
- Quelle: Technologieworkshop – Expertenanforderung
- Aktiv: true
- Ursprung / Begründung der Anforderung: Sicherheit
- Urheber: Tobias Oetermann
- Art der Anforderung: Wunschanforderung
- Verantwortlichkeit: IKA

### R209
Verwendung von recyclebaren Materialien / nachwachsenden Rohstoffen
- Bemerkung: Zum Schutz der Umwelt sollten möglichst viele wiederverwertbare Materialien verwendet werden
- Quelle: Technologieworkshop – Expertenanforderung
- Aktiv: true
- Ursprung / Begründung der Anforderung: Sicherheit
- Urheber: Tobias Oetermann
- Art der Anforderung: Wunschanforderung
- Verantwortlichkeit: IKA, Cerence, CanControls, Charamel, Saint Gobain

### R210
Visualisieren, dass andere Verkehrsteilnehmer gesehen werden
- Bemerkung: Das System sollte erkannte Fahrzeuge (auch aus V2V-Kommunikation) visualisieren
- Quelle: Technologieworkshop – Expertenanforderung
- Aktiv: true
- Ursprung / Begründung der Anforderung: Sicherheit
- Urheber: Tobias Oetermann
- Art der Anforderung: Festanaforderung
- Verantwortlichkeit: Saint Gobain, CanControls, IKA

### R211
Sicherheitsrelevante Interaktionen (indirekte Fahrzeugführung) redundant möglich
- Bemerkung: Sicherheitsrelevante Interaktionen (indirekte Fahrzeugführung) sollte durch die Multimodalität Eingabe redundant möglich sein
- Quelle: Technologieworkshop – Expertenanforderung
- Aktiv: true
- Ursprung / Begründung der Anforderung: Sicherheit
- Urheber: Tobias Oetermann
- Art der Anforderung: Festanaforderung
- Verantwortlichkeit: IKA, Cerence, CanControls

### R212
Die Audioausgabe sollte automatisch in Abhängigkeit des Außengeräuschpegels angepasst werden
- Bemerkung: Die Lautstärke sollte automatisch in Abhängigkeit des Außengeräuschpegels angepasst werden. Der Geräuschpegel kann mit Hilfe der internen Mikrofone gemessen werden.
- Quelle: Technologieworkshop – Expertenanforderung
- Aktiv: true
- Ursprung / Begründung der Anforderung: Sicherheit
- Urheber: Tobias Oetermann
- Art der Anforderung: Wunschanforderung
- Verantwortlichkeit: Cerence

### R213
Fehlbedienung bei Primärstellteilen sicher vermeiden
- Bemerkung: Fehlbedienung bei Primärstellteilen sicher vermeiden (z.B. durch Mitfahrer oder nicht intendierte Eingabe des Nutzers) auch bei indirekter Fahrzeugführung
- Quelle: Technologieworkshop – Expertenanforderung
- Aktiv: true
- Ursprung / Begründung der Anforderung: Sicherheit
- Urheber: Tobias Oetermann
- Art der Anforderung: Festanaforderung
- Verantwortlichkeit: IKA

## R198
Gebrauch
- Quelle: Technologieworkshop – Expertenanforderung
- Aktiv: true
- Urheber: Tobias Oetermann

### R214
Hohe Ausfallsicherheit
- Bemerkung: Das System sollte eine hohe Ausfallsicherheit haben
- Quelle: Technologieworkshop – Expertenanforderung
- Aktiv: true
- Ursprung / Begründung der Anforderung: Gebrauch
- Urheber: Tobias Oetermann
- Art der Anforderung: Festanaforderung
- Verantwortlichkeit: IKA, DFKI, Cerence, CanControls, Charamel, Saint Gobain

### R218
Lebensdauer mindestens 10 Jahre oder 5000 Betriebsstunden
- Bemerkung: Die Lebensdauer des Systems sollte der Lebensdauer des Fahrzeugs entsprechen
- Quelle: Technologieworkshop – Expertenanforderung
- Aktiv: true
- Ursprung / Begründung der Anforderung: Gebrauch
- Urheber: Tobias Oetermann
- Art der Anforderung: Festanaforderung
- Verantwortlichkeit: IKA, DFKI, Cerence, CanControls, Charamel, Saint Gobain

### R216
Lange Wartungsintervalle
- Bemerkung: Das System sollte lange Wartungsintervalle haben
- Quelle: Technologieworkshop – Expertenanforderung
- Aktiv: true
- Ursprung / Begründung der Anforderung: Gebrauch
- Urheber: Tobias Oetermann
- Art der Anforderung: Festanaforderung
- Verantwortlichkeit: IKA, DFKI, Cerence, CanControls, Charamel, Saint Gobain

### R217
Simple/automatische Wartung ermöglichen
- Bemerkung: Ermöglicht einfache/automatische Wartung ggf. durch Online-Updates und Online-Diagnose
- Quelle: Technologieworkshop – Expertenanforderung
- Aktiv: true
- Ursprung / Begründung der Anforderung: Gebrauch
- Urheber: Tobias Oetermann
- Art der Anforderung: Festanaforderung
- Verantwortlichkeit: IKA, DFKI, Cerence, CanControls, Charamel, Saint Gobain

### R219
Die Systemleistung sollte nicht durch Schmutz und Kratzer auf der Windschutzscheibe beeinträchtigt werden
- Bemerkung: Die Systemleistung sollte nicht durch alltägliche Situationen (Schmutz, Regen, Nebel etc.) während der Fahrt beeinträchtigt werden
- Quelle: Technologieworkshop – Expertenanforderung
- Aktiv: true
- Ursprung / Begründung der Anforderung: Gebrauch
- Urheber: Tobias Oetermann
- Art der Anforderung: Festanaforderung
- Verantwortlichkeit: Saint Gobain

### R220
System sollte auch dann funktionieren, wenn die Windschutzscheibe beschlagen ist
- Bemerkung: Es kann vorkommen, dass die Windschutzscheibe beschlagen ist, insbesondere am Anfang der Fahrt. Das System sollte auch in einer solchen Situation fehlerfrei funktionieren.
- Quelle: Technologieworkshop – Expertenanforderung
- Aktiv: true
- Ursprung / Begründung der Anforderung: Gebrauch
- Urheber: Tobias Oetermann
- Art der Anforderung: Festanaforderung
- Verantwortlichkeit: Saint Gobain

### R221
Kein Leistungsabfall mit der Zeit
- Bemerkung: Das System sollte die ursprüngliche Leistung während der gesamten Lebensdauer beibehalten
- Quelle: Technologieworkshop – Expertenanforderung
- Aktiv: true
- Ursprung / Begründung der Anforderung: Gebrauch
- Urheber: Tobias Oetermann
- Art der Anforderung: Festanaforderung
- Verantwortlichkeit: IKA, DFKI, Cerence, CanControls, Charamel, Saint Gobain

### R222
Geräuschlose Mechanik
- Bemerkung: Alle mechanischen Teile sollten während des normalen Betriebs keine Geräusche machen.
- Quelle: Technologieworkshop – Expertenanforderung
- Aktiv: true
- Ursprung / Begründung der Anforderung: Gebrauch
- Urheber: Tobias Oetermann
- Art der Anforderung: Festanaforderung
- Verantwortlichkeit: IKA, Cerence, CanControls, Charamel, Saint Gobain

### R223
Temperaturbereich -30° - +50°
- Bemerkung: Das System sollte in einem Temperaturbereich zwischen -30°C und +50°C fehlerfrei funktionieren
- Quelle: Technologieworkshop – Expertenanforderung
- Aktiv: true
- Ursprung / Begründung der Anforderung: Gebrauch
- Urheber: Tobias Oetermann
- Art der Anforderung: Festanaforderung
- Verantwortlichkeit: IKA, Cerence, CanControls, Charamel, Saint Gobain

### R224
Luftfeuchtigkeitsbeständigkeit
- Bemerkung: Das System sollte in einer Umgebung mit hoher Luftfeuchtigkeit fehlerfrei funktionieren
- Quelle: Technologieworkshop – Expertenanforderung
- Aktiv: true
- Ursprung / Begründung der Anforderung: Gebrauch
- Urheber: Tobias Oetermann
- Art der Anforderung: Festanaforderung
- Verantwortlichkeit: IKA, Cerence, CanControls, Charamel, Saint Gobain

### R225
Avatar (intelligenter Assistent) sollte nur sprechen, wenn es die Situation zulässt
- Bemerkung: Avatar (intelligenter Assistent) spricht nicht durchgehend, sondern analysiert die vorliegende Situation und passt das eigene Verhalten entsprechend an (störend bspw. in Unterhaltung, lesen etc.)
- Quelle: Technologieworkshop – Expertenanforderung
- Aktiv: true
- Ursprung / Begründung der Anforderung: Gebrauch
- Urheber: Tobias Oetermann
- Art der Anforderung: Festanaforderung
- Verantwortlichkeit: Charamel, Cerence, CanCntrols

## R215
Industrial Design
- Quelle: Technologieworkshop – Expertenanforderung
- Aktiv: true
- Urheber: Tobias Oetermann

### R226
Farbpsychologie berücksichtigen
- Bemerkung: Es sollten nur Farben genutzt werden, die das Nutzererlebnis verbessern und das Systemverständnis unterstützen
- Quelle: Technologieworkshop – Expertenanforderung
- Aktiv: true
- Ursprung / Begründung der Anforderung: Industrial Design
- Urheber: Tobias Oetermann
- Art der Anforderung: Wunschanforderung
- Verantwortlichkeit: IKA, Charamel, Saint Gobain

### R227
Stellteil für indirekte Fahrzeugführung fügt sich in Interiordesign ein
- Bemerkung: Das Stellteil für die indirekte Fahrzeugführung sollte sich nicht vom restlichen Innenraum des Fahrzeugs abheben. Es sollten ähnlicher Stil, Farben und Materialien benutzt werden.
- Quelle: Technologieworkshop – Expertenanforderung
- Aktiv: true
- Ursprung / Begründung der Anforderung: Industrial Design
- Urheber: Tobias Oetermann
- Art der Anforderung: Festanaforderung
- Verantwortlichkeit: IKA

### R229
System ermöglicht, die OEM CI zu berücksichtigen
- Bemerkung: Das System sollte sich in den Innenraum des OEMs einfügen. Eine Anpassung hinsichtlich der Farben, des Stils und der Materialien sollte berücksichtigt werden können.
- Quelle: Technologieworkshop – Expertenanforderung
- Aktiv: true
- Ursprung / Begründung der Anforderung: Industrial Design
- Urheber: Tobias Oetermann
- Art der Anforderung: Wunschanforderung
- Verantwortlichkeit: IKA, Cerence, CanControls, Charamel, Saint Gobain

### R230
Design sollte zum Preissegment passen
- Bemerkung: Die Materialauswahl, Anzeigequalität (Hardware) und die Anzeigekonzepte sollten dem Preissegment entsprechen.
  Hochpreissegment: Entsprechend anmutendes Interior (große hochauflösende Bildschirme, edle Bedienteile etc.)
- Quelle: Technologieworkshop – Expertenanforderung
- Aktiv: true
- Ursprung / Begründung der Anforderung: Industrial Design
- Urheber: Tobias Oetermann
- Art der Anforderung: Wunschanforderung
- Verantwortlichkeit: IKA, Cerence, CanControls, Charamel, Saint Gobain

### R231
Avatar sollte wiedererkennbares Aussehen haben
- Bemerkung: Avatar sollte ein wiedererkennbares Aussehen haben, um dem Nutzer zu gefallen und das Vertrauen zu erhöhen
- Quelle: Technologieworkshop – Expertenanforderung
- Aktiv: true
- Ursprung / Begründung der Anforderung: Industrial Design
- Urheber: Tobias Oetermann
- Art der Anforderung: Wunschanforderung
- Verantwortlichkeit: Charamel
- Link -> R232

### R232
Avatar sollte personalisierbar sein
- Bemerkung: Avatar sollte personalisierbar sein: Aussehen, Stimme, Verhalten, ...
- Quelle: Technologieworkshop – Expertenanforderung
- Aktiv: true
- Ursprung / Begründung der Anforderung: Industrial Design
- Urheber: Tobias Oetermann
- Art der Anforderung: Festanaforderung
- Verantwortlichkeit: Charamel

### R233
Anzeige (-konzept) individualisierbar
- Bemerkung: Innerhalb gewisser Konzeptgrenzen sind die Anzeigen an persönliche Vorliebenanpassbar (Anzeigeposition, Anzeigetyp, Farbeusw.)
- Quelle: Technologieworkshop – Expertenanforderung
- Aktiv: true
- Ursprung / Begründung der Anforderung: Industrial Design
- Urheber: Tobias Oetermann
- Art der Anforderung: Festanaforderung
- Verantwortlichkeit: IKA

### R234
Produktwiederkennung & Begrüßung
- Bemerkung: Welcome-Screen (mit Sound) basierend auf Nutzererkennung auf Windschutzscheibe
- Quelle: Technologieworkshop – Expertenanforderung
- Aktiv: true
- Ursprung / Begründung der Anforderung: Industrial Design
- Urheber: Tobias Oetermann
- Art der Anforderung: Wunschanforderung
- Verantwortlichkeit: Saint Gobain, Cerence, CanControls

### R235
Design muss mit Sicherheit kohärent gehen
- Bemerkung: Design muss das Sicherheitsgefühl des Kunden erhöhen
- Quelle: Technologieworkshop – Expertenanforderung
- Aktiv: true
- Ursprung / Begründung der Anforderung: Industrial Design
- Urheber: Tobias Oetermann
- Art der Anforderung: Festanaforderung
- Verantwortlichkeit: IKA, Cerence, CanControls, Charamel, Saint Gobain

## R228
Kosten
- Quelle: Technologieworkshop – Expertenanforderung
- Aktiv: true
- Urheber: Tobias Oetermann

### R236
Hardware redundant nutzen
- Bemerkung: Wenn es möglich ist, Hardware redundant für mehrere Funktionen Verwenden: Mikrofon, Kamera, etc.
- Quelle: Technologieworkshop – Expertenanforderung
- Aktiv: true
- Ursprung / Begründung der Anforderung: Kosten
- Urheber: Tobias Oetermann
- Art der Anforderung: Wunschanforderung
- Verantwortlichkeit: IKA, Cerence, CanControls, Charamel, Saint Gobain

### R239
Verknüpfung von Funktionalitäten
- Bemerkung: Verknüpfung von Funktionalitäten: Hardware zu möglichst vielen Features nutzen (Synergie)
- Quelle: Technologieworkshop – Expertenanforderung
- Aktiv: true
- Ursprung / Begründung der Anforderung: Kosten
- Urheber: Tobias Oetermann
- Art der Anforderung: Wunschanforderung
- Verantwortlichkeit: IKA, Cerence, CanControls, Charamel, Saint Gobain

### R238
COTS (Commercial off-the-shelf) nutzen
- Bemerkung: Soweit möglich COTS nutzen (Kommerzielle Produkte aus dem Regal) um den Endpreis als Entwicklungspreis niedrig zu halten
- Quelle: Technologieworkshop – Expertenanforderung
- Aktiv: true
- Ursprung / Begründung der Anforderung: Kosten
- Urheber: Tobias Oetermann
- Art der Anforderung: Wunschanforderung
- Verantwortlichkeit: IKA, DFKI, Cerence, CanControls, Charamel, Saint Gobain

### R240
Vorhandene Produktionsmöglichkeiten nutzen
- Bemerkung: Soweit möglich auf bestehende Technologie und Produktionslinien für neue Produkte zurückgreifen
- Quelle: Technologieworkshop – Expertenanforderung
- Aktiv: true
- Ursprung / Begründung der Anforderung: Kosten
- Urheber: Tobias Oetermann
- Art der Anforderung: Wunschanforderung
- Verantwortlichkeit: IKA, Cerence, CanControls, Charamel, Saint Gobain

## R237
Hardware / Software
- Quelle: Technologieworkshop – Expertenanforderung
- Aktiv: true
- Urheber: Tobias Oetermann

### R241
V2V nutzen
- Bemerkung: V2V nutzen, wenn nötig/möglich. (bspw. Darstellung von Fahrzeugen hinter Kreuzungen etc.).
- Quelle: Technologieworkshop – Expertenanforderung
- Aktiv: true
- Ursprung / Begründung der Anforderung: Hardware / Software
- Urheber: Tobias Oetermann
- Art der Anforderung: Begeisterungsanforderung
- Verantwortlichkeit: IKA

### R243
Online Updates
- Bemerkung: Übereinstimmung mitECE R-156: Einheitliche Bestimmungen für die Genehmigung von Kraftfahrzeugen hinsichtlich der Softwareaktualisierung und des Softwareaktualisierungsmanagementsystems
- Quelle: Technologieworkshop – Expertenanforderung
- Aktiv: true
- Ursprung / Begründung der Anforderung: Hardware / Software
- Urheber: Tobias Oetermann
- Art der Anforderung: Wunschanforderung
- Verantwortlichkeit: IKA, DFKI, Cerence, CanControls, Charamel, Saint Gobain

### R244
Lernen durch Massen-Daten
- Bemerkung: Maschinelles Lernen (Vertrauensmodell und Nutzerpräferenzen) sollte durch die Massendaten ermöglicht werden
- Quelle: Technologieworkshop – Expertenanforderung
- Aktiv: true
- Ursprung / Begründung der Anforderung: Hardware / Software
- Urheber: Tobias Oetermann
- Art der Anforderung: Festanaforderung
- Verantwortlichkeit: DFKI, CanControls, Cerence

### R245
Datenbank im Backend
- Bemerkung: Datenbank im Backend speichern, um Übertragbarkeit auf andere Fahrzeuge zu ermöglichen (dabei Datenschutz sicherstellen)
- Quelle: Technologieworkshop – Expertenanforderung
- Aktiv: true
- Ursprung / Begründung der Anforderung: Hardware / Software
- Urheber: Tobias Oetermann
- Art der Anforderung: Wunschanforderung
- Verantwortlichkeit: DFKI, CanControls

### R246
Mehrfachnutzung von Sensordaten für unterschiedliche Funktionen ermöglichen
- Bemerkung: Dieselben Sensoren sollten für verschiedene Funktionen verwendet werden (dieselben Kameras werden für die Einschätzung des Benutzervertrauens und für die Einschätzung, ob der Benutzer eingeschlafen ist, verwendet). Auf diese Weise wird die Anzahl der Sensoren reduziert und der Preis des Systems ist niedriger.
- Quelle: Technologieworkshop – Expertenanforderung
- Aktiv: true
- Ursprung / Begründung der Anforderung: Hardware / Software
- Urheber: Tobias Oetermann
- Art der Anforderung: Wunschanforderung
- Verantwortlichkeit: IKA, Cerence, CanControls, Charamel, Saint Gobain

### R247
Erforderliche Rechenleistung minimieren, um Energie zu sparen
- Bemerkung: Das System sollte die benötigte Rechenleistung minimieren, um Energie zu sparen.
- Quelle: Technologieworkshop – Expertenanforderung
- Aktiv: true
- Ursprung / Begründung der Anforderung: Hardware / Software
- Urheber: Tobias Oetermann
- Art der Anforderung: Wunschanforderung
- Verantwortlichkeit: IKA, DFKI, Cerence, CanControls, Charamel, Saint Gobain

### R248
Proprietäre software vermeiden
- Bemerkung: Proprietäre Software bezeichnet Software, die das Recht und die Möglichkeiten der Wieder- und Weiterverwendung sowie Änderung und Anpassung durch Nutzer und Dritte stark einschränkt.
- Quelle: Technologieworkshop – Expertenanforderung
- Aktiv: true
- Ursprung / Begründung der Anforderung: Hardware / Software
- Urheber: Tobias Oetermann
- Art der Anforderung: Wunschanforderung
- Verantwortlichkeit: IKA, DFKI, Cerence, CanControls, Charamel, Saint Gobain

### R249
Nur Nutzer soll Zugriff auf persönliche Daten haben
- Bemerkung: Persönliche Daten sollten geschützt werden. Nur der Nutzer soll Zugriff auf persönliche Daten haben
- Quelle: Technologieworkshop – Expertenanforderung
- Aktiv: true
- Ursprung / Begründung der Anforderung: Hardware / Software
- Urheber: Tobias Oetermann
- Art der Anforderung: Festanaforderung
- Verantwortlichkeit: IKA, DFKI, Cerence, CanControls, Charamel, Saint Gobain

### R250
Hard-und Software müssen austauschbar sein
- Bemerkung: Hard- und Software müssen ausgetauscht/geupdatet werden können, um eine reibungslose Wartung zu realisieren
- Quelle: Technologieworkshop – Expertenanforderung
- Aktiv: true
- Ursprung / Begründung der Anforderung: Hardware / Software
- Urheber: Tobias Oetermann
- Art der Anforderung: Festanaforderung
- Verantwortlichkeit: IKA, Cerence, CanControls, Charamel, Saint Gobain

### R251
Transparenz der Datennutzung
- Bemerkung: Der Benutzer muss vollständig darüber informiert werden, wie die Fahrzeugdaten gesammelt werden und wie sie genutzt werden.
- Quelle: Technologieworkshop – Expertenanforderung
- Aktiv: true
- Ursprung / Begründung der Anforderung: Hardware / Software
- Urheber: Tobias Oetermann
- Art der Anforderung: Festanaforderung
- Verantwortlichkeit: CanControls, Cerence, DFKI

### R252
Anonymisierte Nutzung der Bewegungs-/Fahrzeugdaten
- Bemerkung: Die vom Fahrzeug gesammelten Daten sollten nur zu dem Zweck gesammelt werden, die Arbeit des Systems zu verbessern, und sie sollten vollständig anonymisiertwerden.
- Quelle: Technologieworkshop – Expertenanforderung
- Aktiv: true
- Ursprung / Begründung der Anforderung: Hardware / Software
- Urheber: Tobias Oetermann
- Art der Anforderung: Festanaforderung
- Verantwortlichkeit: CanControls, Cerence, DFKI

## R242
Nutzeranforderungen
- Quelle: Nutzeranforderungen aus Expertensicht
- Aktiv: true
- Ursprung / Begründung der Anforderung: Nutzeranforderung
- Urheber: Tobias Oetermann

### R253
Fahrzeug passt sich den Benutzergewohnheiten an
- Bemerkung: Fahrzeug lernt von den Benutzergewohnheiten und schlägt das Ziel und den Modus vor
- Quelle: Nutzeranforderungen aus Expertensicht
- Aktiv: true
- Ursprung / Begründung der Anforderung: Nutzeranforderung
- Urheber: Tobias Oetermann
- Art der Anforderung: Begeisterungsanforderung
- Verantwortlichkeit: IKA

### R254
Fahrzeug kann über das Handy mit dem Nutzer kommunizieren
- Bemerkung: Wichtige Informationen zwischen dem Fahrzeug und dem Nutzer werden über das Mobiltelefon ausgetauscht, während sich dieser nicht im Fahrzeug befindet. Fahrzeug-Status lässt sich übereine Smartphone-App abrufen. Fahrzeug kann mittels Smartphone-GPS die Lokation des Nutzers bestimmen, um den Abholpunkt zu definieren.
- Quelle: Nutzeranforderungen aus Expertensicht
- Aktiv: true
- Ursprung / Begründung der Anforderung: Nutzeranforderung
- Urheber: Tobias Oetermann
- Art der Anforderung: Begeisterungsanforderung
- Verantwortlichkeit: IKA

### R255
Kalenderbasierte Fahrzeugvorbereitung
- Bemerkung: Fahrzeug kann Temperatur und Lüftung anpassen, bevor der Nutzer einsteigt. Fahrzeug kennt den Kalender des Nutzers und kann den Ladezustand der Batterie entsprechend der zu erwartenden Nutzung vorbereiten.
- Quelle: Nutzeranforderungen aus Expertensicht
- Aktiv: true
- Ursprung / Begründung der Anforderung: Nutzeranforderung
- Urheber: Tobias Oetermann
- Art der Anforderung: Begeisterungsanforderung
- Verantwortlichkeit: IKA

### R256
Fahrstil passt sich den Benutzeraktivitäten an
- Bemerkung: Fahrstil adaptiert sich an die aktuelle Nutzersituation und den Nutzerzustand (Vertrauenslevel, Nebentätigkeit wie z.B. Arbeiten etc.)
- Quelle: Nutzeranforderungen aus Expertensicht
- Aktiv: true
- Ursprung / Begründung der Anforderung: Nutzeranforderung
- Urheber: Tobias Oetermann
- Art der Anforderung: Wunschanforderung
- Verantwortlichkeit: CanControls, Cerence, IKA
